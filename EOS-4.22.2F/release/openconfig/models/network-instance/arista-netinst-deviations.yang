module arista-netinst-deviations {
  namespace "http://arista.com/yang/openconfig/network-instances/deviations";
  prefix arista-network-instances-deviations;

  import openconfig-network-instance {
    prefix oc-netinst;
  }
  import openconfig-network-instance-types {
	prefix oc-ni-types;
  }

  organization
    "Arista Networks, Inc.";
  contact
    "Arista Networks, Inc.
     Product Support";
  description
    "This module contains OpenConfig Network Instances deviations in Arista EOS.

     Copyright (c) 2017 Arista Networks, Inc. All rights reserved.";

  revision 2019-05-24 {
	description
	  "Add prefixes to identity names in must statement.";
  }

  revision 2017-11-10 {
    description
      "Initial deviation file.";
  }

  deviation "/oc-netinst:network-instances/oc-netinst:network-instance/oc-netinst:inter-instance-policies/oc-netinst:apply-policy/oc-netinst:config/oc-netinst:default-import-policy" {
    description
      "default-import-policy is REJECT_ROUTE in EOS";
    deviate add {
      must "../default-import-policy = 'REJECT_ROUTE'" {
        error-message "default-import-policy can only be set to REJECT_ROUTE in EOS";
      }
    }
    deviate replace {
      default "REJECT_ROUTE";
    }
  }

  deviation "/oc-netinst:network-instances/oc-netinst:network-instance/oc-netinst:state/oc-netinst:enabled" {
    description
      "EOS VRFs state doesn't map to a single leaf";
    deviate not-supported;
  }

  deviation "/oc-netinst:network-instances/oc-netinst:network-instance/oc-netinst:config/oc-netinst:enabled" {
    description
      "a global enabled command for VRFs is not fully supported in EOS";
    deviate not-supported;
  }

  deviation "/oc-netinst:network-instances/oc-netinst:network-instance/oc-netinst:config" {
    description
      "only default and L3 instances are supported in EOS";
    deviate add {
      must "(type='oc-ni-types:DEFAULT_INSTANCE' and name='default') or (type='oc-ni-types:L3VRF' and name!='default')";
    }
  }

  deviation "/oc-netinst:network-instances/oc-netinst:network-instance/oc-netinst:vlans/oc-netinst:vlan/oc-netinst:members/oc-netinst:member/oc-netinst:state/oc-netinst:interface" {
    description
      "member interface can be an interface other than openconfig-interfaces:base-interface-ref, such as a subinterface, etc";
    deviate replace {
      type string;
    }
  }
}
