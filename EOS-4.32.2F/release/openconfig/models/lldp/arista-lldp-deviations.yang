module arista-lldp-deviations {
  namespace "http://arista.com/yang/openconfig/lldp/deviations";
  prefix arista-lldp-deviations;

  import openconfig-lldp {
    prefix oc-lldp;
  }
  import openconfig-extensions {
    prefix oc-ext;
  }

  organization
    "Arista Networks, Inc.";
  contact
    "Arista Networks, Inc.
     Product Support";
  description
    "This module contains OpenConfig lldp deviations in Arista EOS.

     Copyright (c) 2017 Arista Networks, Inc. All rights reserved.";
  oc-ext:openconfig-version "1.1.0";

  revision 2022-01-17 {
    description
      "Enable the configuration of system-name and system-description tlvs";
    reference
      "1.1.0";
  }
  revision 2021-09-27 {
    description
      "fix pyang BAD_DEVIATE_ADD error";
    reference
      "1.0.3";
  }
  revision 2020-11-30 {
    description
      "Fix errors reported by pyang.";
    reference
      "1.0.2";
  }
  revision 2018-04-02 {
    description
      "Added deviation for the LLDP interface enabled config.";
    reference
      "1.0.1";
  }
  revision 2017-09-07 {
    description
      "Initial deviations file.";
    reference
      "1.0.0";
  }

  deviation "/oc-lldp:lldp/oc-lldp:config/oc-lldp:chassis-id" {
    description
      "chassis-id is reported but not configurable in EOS";
    deviate replace {
      config false;
    }
  }

  deviation "/oc-lldp:lldp/oc-lldp:config/oc-lldp:chassis-id-type" {
    description
      "chassis-id-type is reported but not configurable in EOS";
    deviate replace {
      config false;
    }
  }

  deviation "/oc-lldp:lldp/oc-lldp:interfaces/oc-lldp:interface/oc-lldp:config/oc-lldp:enabled" {
    description
      "EOS allows the transmission and receiving of LLDP packets on an interface to be configured independently";
    deviate replace {
      type union {
        type boolean;
        type enumeration {
          enum TRANSMIT {
            description
              "Only enable transmission of LLDP packets on the interface.";
          }
          enum RECEIVE {
            description
              "Only enable receiving LLDP packets on the interface.";
          }
        }
      }
      default "true";
    }
  }

  deviation "/oc-lldp:lldp/oc-lldp:interfaces/oc-lldp:interface/oc-lldp:state/oc-lldp:enabled" {
    description
      "EOS allows the transmission and receiving of LLDP packets on an interface to be configured independently";
    deviate replace {
      type union {
        type boolean;
        type enumeration {
          enum TRANSMIT {
            description
              "Only enable transmission of LLDP packets on the interface.";
          }
          enum RECEIVE {
            description
              "Only enable receiving LLDP packets on the interface.";
          }
        }
      }
      default "true";
    }
  }

  deviation "/oc-lldp:lldp/oc-lldp:interfaces/oc-lldp:interface/oc-lldp:neighbors/oc-lldp:neighbor/oc-lldp:state/oc-lldp:last-update" {
    description
      "last-update is not supported. Please see last-update-time instead";
    deviate not-supported;
  }

  deviation "/oc-lldp:lldp/oc-lldp:interfaces/oc-lldp:interface/oc-lldp:neighbors/oc-lldp:neighbor/oc-lldp:state/oc-lldp:age" {
    description
      "age is not supported. Please see registration-time instead";
    deviate not-supported;
  }
}
