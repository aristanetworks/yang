module arista-l1-open-config-phy-model {
  yang-version 1;
  namespace "http://arista.com/yang/experimental/eos/arista-l1-open-config-phy-model";
  prefix "arista-l1-open-config-phy-model";

  import openconfig-extensions { prefix "oc-ext"; }
  import openconfig-if-ethernet { prefix "openconfig-if-ethernet"; }
  import openconfig-interfaces { prefix "openconfig-interfaces"; }
  organization
    "Arista Networks <http://arista.com/>";
  contact
    "Arista Networks <http://arista.com/>";
  description
    "Attributes related to interface phy components

    THIS YANG MODULE WAS GENERATED. DO NOT EDIT THIS FILE.";

  oc-ext:openconfig-version "1.0.0";

  revision "2023-12-05" {
    description
      "Version 1.0.0, generated on 2023-12-05";
    reference "1.0.0";
  }

  grouping intf-phy-lane-index {
    leaf intf-name {
      type string;
      description
        "The interface name (eg, EthernetX/Y)";
    }
    leaf phy-index {
      type uint16;
      description
        "The index of the phy (0 is the phy in the ASIC)";
    }
    leaf lane {
      type uint16;
      description
        "The lane number (0 based)";
    }
    description
      "Index for a lane based phy attribute";
  }
  grouping intf-phy-index {
    leaf intf-name {
      type string;
      description
        "The interface name (eg, EthernetX/Y)";
    }
    leaf phy-index {
      type uint16;
      description
        "The index of the phy (0 is the phy in the ASIC)";
    }
    description
      "Index for a phy attribute";
  }
  grouping pcs-lane-state {
    uses intf-phy-lane-index;
    description
      "Lane based attributes for the physical coding sublayer";
  }
  grouping pcs-lane-ingress-container {
    list state {
      key "intf-name phy-index lane";
      uses pcs-lane-state;
      description
        "The lane based ingress state container for pcs";
    }
    leaf name {
      type string;
      description
        "name of the grouping";
    }
    description
      "Container for the ingress pcs lane component";
  }
  grouping pcs-lane-egress-container {
    list state {
      key "intf-name phy-index lane";
      uses pcs-lane-state;
      description
        "The lane based egress state container for pcs";
    }
    leaf name {
      type string;
      description
        "name of the grouping";
    }
    description
      "Container for the egress pcs lane component";
  }
  grouping pcs-state {
    uses intf-phy-index;
    leaf error-blocks {
      type uint32;
      description
        "errorBlocks";
    }
    description
      "Attributes for the physical coding sublayer";
  }
  grouping pcs-ingress-container {
    list state {
      key "intf-name phy-index";
      uses pcs-state;
      description
        "The ingress state container for pcs";
    }
    leaf name {
      type string;
      description
        "name of the grouping";
    }
    description
      "Container for the ingress pcs component";
  }
  grouping pcs-egress-container {
    list state {
      key "intf-name phy-index";
      uses pcs-state;
      description
        "The egress state container for pcs";
    }
    leaf name {
      type string;
      description
        "name of the grouping";
    }
    description
      "Container for the egress pcs component";
  }
  grouping fec-state {
    uses intf-phy-index;
    leaf pre-fec-ber {
      type binary {
         length 8;
      }
      description
        "preFecBer";
    }
    leaf uncorrected-codewords {
      type uint32;
      description
        "uncorrectedCodewords";
    }
    description
      "Attributes for the forward error correction layer";
  }
  grouping fec-ingress-container {
    list state {
      key "intf-name phy-index";
      uses fec-state;
      description
        "The ingress state container for fec";
    }
    leaf name {
      type string;
      description
        "name of the grouping";
    }
    description
      "Container for the ingress fec component";
  }
  grouping fec-egress-container {
    list state {
      key "intf-name phy-index";
      uses fec-state;
      description
        "The egress state container for fec";
    }
    leaf name {
      type string;
      description
        "name of the grouping";
    }
    description
      "Container for the egress fec component";
  }
  augment "/openconfig-interfaces:interfaces/openconfig-interfaces:interface/openconfig-if-ethernet:ethernet" {
  container phys {
    list phy {
      key "index";
      leaf index {
        type string;
        description
          "index leaf used as key for phy list";
      }
      container ingress {
        container pcs {
          container lanes {
            list lane {
              key "lane";
              leaf lane {
                type string;
                description
                  "lane leaf used as key for lane list";
              }
              container state {
                config false;
     uses pcs-lane-state;
     description
         "state container";
      }
        description
         "lane list";
      }
        description
         "lanes container";
      }
                   container state {
                  config false;
     uses pcs-state;
     description
         "state container";
      }
        description
         "pcs container";
      }
                     container fec {
                    container state {
                      config false;
     uses fec-state;
     description
         "state container";
      }
        description
         "fec container";
      }
        description
         "ingress container";
      }
                         container egress {
                        container pcs {
                          container lanes {
                            list lane {
                              key "lane";
                              leaf lane {
                                type string;
                                description
                                  "lane leaf used as key for lane list";
                              }
                              container state {
                                config false;
     uses pcs-lane-state;
     description
         "state container";
      }
        description
         "lane list";
      }
        description
         "lanes container";
      }
                                   container state {
                                  config false;
     uses pcs-state;
     description
         "state container";
      }
        description
         "pcs container";
      }
                                     container fec {
                                    container state {
                                      config false;
     uses fec-state;
     description
         "state container";
      }
        description
         "fec container";
      }
        description
         "egress container";
      }
        description
         "phy list";
      }
        description
         "phys container";
      }
   }
}
