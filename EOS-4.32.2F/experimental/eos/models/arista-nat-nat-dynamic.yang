module arista-nat-nat-dynamic {
  yang-version 1;
  namespace "http://arista.com/yang/experimental/eos/arista-nat-nat-dynamic";
  prefix "arista-nat-nat-dynamic";

  import openconfig-extensions { prefix "oc-ext"; }
  import arista-arnet-conn-tuple { prefix "arista-arnet-conn-tuple"; }
  import arista-arnet-ip { prefix "arista-arnet-ip"; }
  import arista-eos-types { prefix "arista-eos-types"; }
  import arista-exp-eos { prefix "arista-exp-eos"; }
  import arista-nat-nat { prefix "arista-nat-nat"; }
  import openconfig-interfaces { prefix "openconfig-interfaces"; }
  organization
    "Arista Networks <http://arista.com/>";
  contact
    "Arista Networks <http://arista.com/>";
  description
    "Yang model for Dynamic NAT connection.

    THIS YANG MODULE WAS GENERATED. DO NOT EDIT THIS FILE.";

  oc-ext:openconfig-version "0.1.0";

  revision "2022-03-28" {
    description
      "Version 0.1.0, generated on 2022-03-28";
    reference "0.1.0";
  }

  grouping dynamic-connection-key {
    leaf profile-or-interface-id {
      type openconfig-interfaces:interface-id;
      description
        "Identifier of a profile or an interface";
    }
    container conn-tuple {
      uses arista-arnet-conn-tuple:conn-tuple;
      description
        "Information of the connection.";
    }
    description
      "Identifier for dynamic connection.";
  }
  grouping dynamic-connection {
    container key {
      uses dynamic-connection-key;
      description
        "Identifier of the connection.";
    }
    container global-address {
      uses arista-arnet-ip:ip-and-port;
      description
        "Address used for the translation of the connection.";
    }
    container attributes {
      uses arista-nat-nat:dynamic-connection-flags;
      description
        "Stores some specific information about the connection.";
    }
    description
      "A NAT rule to always translate a specific  dynamic connection.";
  }
  grouping dynamic-connection-counter {
    leaf key {
      type openconfig-interfaces:interface-id;
      description
        "Identifier of an interface or a profile.";
    }
    leaf connection-count {
      type uint64;
      description
        "Number of dynamic connection.";
    }
    leaf twice-connection-count {
      type uint64;
      description
        "Number of dynamic twice NAT connection.";
    }
    leaf fullcone-connection-count {
      type uint64;
      description
        "Number of dynamic fullcone NAT connections.";
    }
    leaf symmetric-connection-count {
      type uint64;
      description
        "Number of dynamic symmetric NAT connections.";
    }
    description
      "Number of dynamic connection handled by the control plane, per interface or profile.";
  }
  grouping dynamic-connection-status {
    list dynamic-connection {
      key "key__profile-or-interface-id key__conn-tuple__src-addr__ip key__conn-tuple__src-addr__port key__conn-tuple__dst-addr__ip key__conn-tuple__dst-addr__port key__conn-tuple__proto";
      leaf key__profile-or-interface-id {
        type leafref {
           path "../key/profile-or-interface-id";
        }
        description
          "Identifier of a profile or an interface";
      }
      leaf key__conn-tuple__src-addr__ip {
        type leafref {
           path "../key/conn-tuple/src-addr/ip";
        }
        description
          "IPv4 address of the connection.";
      }
      leaf key__conn-tuple__src-addr__port {
        type leafref {
           path "../key/conn-tuple/src-addr/port";
        }
        description
          "Port of the connection.";
      }
      leaf key__conn-tuple__dst-addr__ip {
        type leafref {
           path "../key/conn-tuple/dst-addr/ip";
        }
        description
          "IPv4 address of the connection.";
      }
      leaf key__conn-tuple__dst-addr__port {
        type leafref {
           path "../key/conn-tuple/dst-addr/port";
        }
        description
          "Port of the connection.";
      }
      leaf key__conn-tuple__proto {
        type leafref {
           path "../key/conn-tuple/proto";
        }
        description
          "IP Protocol used by the connection.";
      }
      uses dynamic-connection;
      description
        "List of dynamic NAT connection handled by the system.";
    }
    list counter {
      key "key";
      uses dynamic-connection-counter;
      description
        "Number of dynamic connection handled by the control plane, per interface or profile.";
    }
    leaf name {
      type string;
      description
        "name of the grouping";
    }
    description
      "Status of dynamic NAT connection in the system.";
  }
  grouping dynamic-connection-hw {
    container key {
      uses dynamic-connection-key;
      description
        "Identifier of the connection.";
    }
    container global-address {
      uses arista-arnet-ip:ip-and-port;
      description
        "Address used for the translation of the connection.";
    }
    container attributes {
      uses arista-nat-nat:dynamic-connection-flags;
      description
        "Stores some specific information about the connection.";
    }
    leaf last-changed-time {
      type arista-eos-types:seconds;
      description
        "Time in second since the last packet of the connection was seen by the forwarding plane.";
    }
    description
      "A NAT rule to always translate a specific  dynamic connection.";
  }
  grouping dynamic-connection-hw-counter {
    leaf key {
      type openconfig-interfaces:interface-id;
      description
        "Identifier of an interface or a profile.";
    }
    leaf connection-count {
      type uint64;
      description
        "Number of dynamic connection.";
    }
    leaf fullcone-connection-count {
      type uint64;
      description
        "Number of dynamic fullcone NAT connections in HW.";
    }
    leaf symmetric-connection-count {
      type uint64;
      description
        "Number of dynamic symmetric NAT connections in HW.";
    }
    description
      "Number of dynamic connection handled by the forwarding plane, per interface or profile.";
  }
  grouping dynamic-connection-hw-status {
    list dynamic-connection-hw {
      key "key__profile-or-interface-id key__conn-tuple__src-addr__ip key__conn-tuple__src-addr__port key__conn-tuple__dst-addr__ip key__conn-tuple__dst-addr__port key__conn-tuple__proto";
      leaf key__profile-or-interface-id {
        type leafref {
           path "../key/profile-or-interface-id";
        }
        description
          "Identifier of a profile or an interface";
      }
      leaf key__conn-tuple__src-addr__ip {
        type leafref {
           path "../key/conn-tuple/src-addr/ip";
        }
        description
          "IPv4 address of the connection.";
      }
      leaf key__conn-tuple__src-addr__port {
        type leafref {
           path "../key/conn-tuple/src-addr/port";
        }
        description
          "Port of the connection.";
      }
      leaf key__conn-tuple__dst-addr__ip {
        type leafref {
           path "../key/conn-tuple/dst-addr/ip";
        }
        description
          "IPv4 address of the connection.";
      }
      leaf key__conn-tuple__dst-addr__port {
        type leafref {
           path "../key/conn-tuple/dst-addr/port";
        }
        description
          "Port of the connection.";
      }
      leaf key__conn-tuple__proto {
        type leafref {
           path "../key/conn-tuple/proto";
        }
        description
          "IP Protocol used by the connection.";
      }
      uses dynamic-connection-hw;
      description
        "List of dynamic NAT connection handled by the forwarding plane.";
    }
    list counter {
      key "key";
      uses dynamic-connection-hw-counter;
      description
        "Number of dynamic connection handled by the forwarding plane, per interface or profile.";
    }
    leaf name {
      type string;
      description
        "name of the grouping";
    }
    description
      "Status of dynamic NAT connection in the system.";
  }
  augment "/arista-exp-eos:arista/arista-nat-nat:ip/arista-nat-nat:nat/arista-nat-nat:status" {
  container dynamic-connection {
    config false;
     uses dynamic-connection-status;
     description
         "dynamic-connection container";
      }
       container dynamic-connection-hardware {
      config false;
     uses dynamic-connection-hw-status;
     description
         "dynamic-connection-hardware container";
      }
   }
}
