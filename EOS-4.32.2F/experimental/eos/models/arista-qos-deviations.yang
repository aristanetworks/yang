module arista-qos-deviations {
  namespace "http://arista.com/yang/openconfig/qos/deviations";
  prefix arista-qos-deviations;

  import openconfig-qos {
    prefix oc-qos;
  }

  import openconfig-extensions {
    prefix oc-ext;
  }

  organization
    "Arista Networks, Inc.";
  contact
    "Arista Networks, Inc.
     Product Support";
  description
    "This module contains OpenConfig QoS augments in Arista EOS.

     Copyright (c) 2024 Arista Networks, Inc. All rights reserved.";
  oc-ext:openconfig-version "1.0.0";

  revision 2024-02-28 {
    description
      "Initial deviation file.";
    reference
      "1.0.0";
  }

  deviation "/oc-qos:qos/oc-qos:queue-management-profiles/oc-qos:queue-management-profile/oc-qos:wred/oc-qos:uniform/oc-qos:config/oc-qos:weight" {
    description
      "queue management profile wred weight range is restricted in EOS";
    deviate replace {
      type uint32 {
        range "0..15";
      }
    }
  }

  deviation "/oc-qos:qos/oc-qos:queue-management-profiles/oc-qos:queue-management-profile/oc-qos:wred/oc-qos:uniform/oc-qos:config/oc-qos:min-threshold" {
    description
      "queue management profile wred min-threshold range is restricted in EOS";
    deviate replace {
      type uint32 {
        range "0..4294967294";
      }
    }
  }

  deviation "/oc-qos:qos/oc-qos:queue-management-profiles/oc-qos:queue-management-profile/oc-qos:wred/oc-qos:uniform/oc-qos:config/oc-qos:max-threshold" {
    description
      "queue management profile wred max-threshold range is restricted in EOS";
    deviate replace {
      type uint32 {
        range "0..4294967294";
      }
    }
  }
}
