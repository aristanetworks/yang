module arista-rpol-augments {
  namespace "http://arista.com/yang/openconfig/policy/augments";
  prefix arista-rpol-augments;

  import openconfig-bgp-policy {
    prefix oc-bgp-pol;
  }
  import openconfig-bgp-types {
    prefix oc-bgp-types;
  }
  import openconfig-routing-policy {
    prefix oc-rpol;
  }
  import arista-rpol-deviations {
    prefix arpol-deviations;
  }
  import openconfig-extensions {
    prefix oc-ext;
  }
  import openconfig-inet-types {
   prefix oc-inet;
  }

  organization
    "Arista Networks <http://arista.com/>";
  contact
    "Arista Networks, Inc.
     Product Support";
  description
    "This module contains OpenConfig routing-policy augments in Arista EOS.

     Copyright (c) 2018 Arista Networks, Inc. All rights reserved.";
  oc-ext:openconfig-version "1.0.3";

  revision 2024-06-24 {
    description
      "Add policy-type leaf for policy definitions.";
    reference
      "1.3.0";
  }
  revision 2024-04-04 {
    description
      "Deprecate community-set-ref-list config and state leafs";
    reference
      "1.2.1";
  }

  revision 2023-08-21 {
    description
      "Remove augment for RCF function definitions.";
    reference
      "1.2.0";
  }
  revision 2023-06-01 {
    description
      "Added augment for RCF function definitions.";
    reference
      "1.1.0";
  }
  revision 2022-10-14 {
    description
      "Added default leaf value for asn-prepend-type.";
    reference
      "1.0.3";
  }
  revision 2022-08-16 {
    description
      "Added two new augment set-as-path-prepend-type and set-as-path-prepend-list.";
    reference
      "1.0.2";
  }
  revision 2020-11-30 {
    description
      "Fix errors reported by pyang.";
    reference
      "1.0.1";
  }
  revision 2018-04-12 {
    description
      "Initial augment file.";
    reference
      "1.0.0";
  }

  augment "/oc-rpol:routing-policy/oc-rpol:policy-definitions/oc-rpol:policy-definition/oc-rpol:statements/oc-rpol:statement/oc-rpol:state" {
    leaf sequence-number {
      type uint32;
      description
        "EOS stores policy entries in a collection keyed by an integer";
    }
    description
      "Add sequence number to Routing Policy state.";
  }

  typedef arista-policy-type {
    type enumeration {
      enum "ROUTE_MAP" {
        description
          "Route map.";
      }
      enum "RCF" {
        description
          "RCF function.";
      }
    }
    description
      "Enumerates the EOS policy engines that can be used as the backend of a policy definition.";
  }

  augment "/oc-rpol:routing-policy/oc-rpol:policy-definitions/oc-rpol:policy-definition/oc-rpol:config" {
    leaf policy-type {
      type arista-policy-type;
      default "ROUTE_MAP";
      description
        "Specify the EOS policy engine to be used as the backend of a policy definition.";
    }
    description
      "Add routing policy type parameters";
  }

  augment "/oc-rpol:routing-policy/oc-rpol:policy-definitions/oc-rpol:policy-definition/oc-rpol:state" {
    leaf policy-type {
      type arista-policy-type;
      default "ROUTE_MAP";
      description
        "Specify the EOS policy engine to be used as the backend of a policy definition.";
    }
    description
      "Add routing policy type parameters";
  }

  augment "/oc-rpol:routing-policy/oc-rpol:policy-definitions/oc-rpol:policy-definition/oc-rpol:statements/oc-rpol:statement/oc-rpol:actions/oc-bgp-pol:bgp-actions/oc-bgp-pol:set-community/oc-bgp-pol:inline" {
    when "../config/method = 'INLINE'" {
      description
        "Active only when the set-community method is INLINE";
    }
    description
      "Add constraint for set-community In-line configuration.";
  }

  augment "/oc-rpol:routing-policy/oc-rpol:policy-definitions/oc-rpol:policy-definition/oc-rpol:statements/oc-rpol:statement/oc-rpol:actions/oc-bgp-pol:bgp-actions/oc-bgp-pol:set-community/oc-bgp-pol:reference" {
    when "../config/method = 'REFERENCE'" {
      description
        "Active only when the set-community method is REFERENCE";
    }
    description
      "Add constraint for set-community Reference configuration.";
  }

  augment "/oc-rpol:routing-policy/oc-rpol:policy-definitions/oc-rpol:policy-definition/oc-rpol:statements/oc-rpol:statement/oc-rpol:actions/oc-bgp-pol:bgp-actions/oc-bgp-pol:set-ext-community/oc-bgp-pol:inline" {
    when "../config/method = 'INLINE'" {
      description
        "Active only when the set-ext-community method is INLINE";
    }
    description
      "Add constraint for set-ext-community In-line configuration.";
  }

  augment "/oc-rpol:routing-policy/oc-rpol:policy-definitions/oc-rpol:policy-definition/oc-rpol:statements/oc-rpol:statement/oc-rpol:actions/oc-bgp-pol:bgp-actions/oc-bgp-pol:set-ext-community/oc-bgp-pol:inline/oc-bgp-pol:config" {
    leaf-list arista-communities {
      type union {
        type arpol-deviations:arista-bgp-ext-community-type;
        type enumeration {
          enum NONE {
            description
              "Remove existing communities, if any";
          }
        }
      }
      description
        "A list of communities for set-ext-community configuration.";
    }
    description
      "Add list for supporting multiple communities in set-ext-community configuration.";
  }

  augment "/oc-rpol:routing-policy/oc-rpol:policy-definitions/oc-rpol:policy-definition/oc-rpol:statements/oc-rpol:statement/oc-rpol:actions/oc-bgp-pol:bgp-actions/oc-bgp-pol:set-ext-community/oc-bgp-pol:inline/oc-bgp-pol:state" {
    leaf-list arista-communities {
      type union {
        type arpol-deviations:arista-bgp-ext-community-type;
        type enumeration {
          enum NONE {
            description
              "Remove existing communities, if any";
          }
        }
      }
      description
        "A list of communities for set-ext-community state.";
    }
    description
      "Add list for supporting multiple communities in set-ext-community state.";
  }

  augment "/oc-rpol:routing-policy/oc-rpol:policy-definitions/oc-rpol:policy-definition/oc-rpol:statements/oc-rpol:statement/oc-rpol:actions/oc-bgp-pol:bgp-actions/oc-bgp-pol:set-community/oc-bgp-pol:inline/oc-bgp-pol:config" {
    leaf-list arista-communities {
      type union {
        type oc-bgp-types:bgp-std-community-type;
        type oc-bgp-types:bgp-well-known-community-type;
        type enumeration {
          enum NONE {
            description
              "Remove existing communities, if any";
          }
        }
      }
      description
        "A list of communities for set-community configuration.";
    }
    description
      "Add list for supporting multiple communities in set-community configuration.";
  }

  augment "/oc-rpol:routing-policy/oc-rpol:policy-definitions/oc-rpol:policy-definition/oc-rpol:statements/oc-rpol:statement/oc-rpol:actions/oc-bgp-pol:bgp-actions/oc-bgp-pol:set-community/oc-bgp-pol:inline/oc-bgp-pol:state" {
    leaf-list arista-communities {
      type union {
        type oc-bgp-types:bgp-std-community-type;
        type oc-bgp-types:bgp-well-known-community-type;
        type enumeration {
          enum NONE {
            description
              "Remove existing communities, if any";
          }
        }
      }
      description
        "A list of communities for set-community state.";
    }
    description
      "Add list for supporting multiple communities in set-community state.";
  }

  augment "/oc-rpol:routing-policy/oc-rpol:policy-definitions/oc-rpol:policy-definition/oc-rpol:statements/oc-rpol:statement/oc-rpol:actions/oc-bgp-pol:bgp-actions/oc-bgp-pol:set-community/oc-bgp-pol:reference/oc-bgp-pol:config" {
    leaf-list community-set-ref-list {
      type leafref {
        path "/oc-rpol:routing-policy/oc-rpol:defined-sets/"
           + "oc-bgp-pol:bgp-defined-sets/"
           + "oc-bgp-pol:community-sets/oc-bgp-pol:community-set/"
           + "oc-bgp-pol:community-set-name";
      }
      status deprecated;
      description
        "A list of community-set.";
    }
    description
      "EOS allows configuring multiple community-lists as part of set-community clause.";
  }

  augment "/oc-rpol:routing-policy/oc-rpol:policy-definitions/oc-rpol:policy-definition/oc-rpol:statements/oc-rpol:statement/oc-rpol:actions/oc-bgp-pol:bgp-actions/oc-bgp-pol:set-community/oc-bgp-pol:reference/oc-bgp-pol:state" {
    leaf-list community-set-ref-list {
      type leafref {
        path "/oc-rpol:routing-policy/oc-rpol:defined-sets/"
           + "oc-bgp-pol:bgp-defined-sets/"
           + "oc-bgp-pol:community-sets/oc-bgp-pol:community-set/"
           + "oc-bgp-pol:community-set-name";
      }
      status deprecated;
      description
        "A list of community-set.";
    }
    description
      "EOS allows configuring multiple community-lists as part of set-community clause.";
  }

  grouping as-path-prepend-type {
    description
      "Configuration data for the AS path prepend type action.";

    leaf asn-prepend-type {
      type enumeration {
        enum "SINGLE" {
          description
            "Single AS number to prepend to AS path with specified number of times.";
        }
        enum "MULTIPLE" {
          description
            "multiple AS number to prepend to AS path.";
        }
      }
      default "SINGLE";
      description
        "AS number prepends in AS path depends on asn-prepend-type leaf.
        Single AS number is repeated by specified number of time to prepend
        in AS path if asn-prepend-type leaf is SINGLE. Multiple AS numbers
        specified to prepend to AS path if asn-prepend-type is MULTIPLE.";
    }
  }

  augment "/oc-rpol:routing-policy/oc-rpol:policy-definitions/oc-rpol:policy-definition/oc-rpol:statements/oc-rpol:statement/oc-rpol:actions/oc-bgp-pol:bgp-actions" {
    container set-as-path-prepend-type {
      description
        "Action to specify AS path prepend type to prepend
        single AS number repeated multiple time or multiple
        AS numbers.";
      container config {
        description
          "Configuration data for the AS path prepend type action.";
        uses as-path-prepend-type;
      }
      container state {
        config false;
        description
          "Operational state data for the AS path prepend type action.";
        uses as-path-prepend-type;
      }
    }
    description
      "EOS allows configuring single or multiple AS number to prepend in AS path.";
  }

  grouping as-path-prepend-list {
    description
      "Configuration data for list of AS numbers for AS path prepend action.";
    leaf index {
      type uint32;
      description
        "Index of AS number added in the list for AS path perpend.";
    }
    leaf asn {
       type oc-inet:as-number;
       description
        "AS number added in the list for AS path prepend.";
    }
  }

  grouping as-path-prepend-list-repeat {
    description
      "Configuration data for repeat the number of times asn list is specified to the AS path.";
    leaf repeat {
      type uint8 {
        range "1..64";
      }
      default "1";
      description
        "Number of times to prepend the value specified in the asn list to the AS path.";
    }
  }

  augment "/oc-rpol:routing-policy/oc-rpol:policy-definitions/oc-rpol:policy-definition/oc-rpol:statements/oc-rpol:statement/oc-rpol:actions/oc-bgp-pol:bgp-actions" {
    container set-as-path-prepend-list {
      when "../set-as-path-prepend-type/config/asn-prepend-type='MULTIPLE'";
      description
        "Action to prepend the specified multiple AS numbers to the AS path and specified number of time list is repeated.";
      container config {
        description
          "Configuration data for repitition of AS number list in AS path prepend action.";
        uses as-path-prepend-list-repeat;
      }
      container state {
        config false;
        description
          "Operational state for repitition of AS number list in AS path prepend action.";
        uses as-path-prepend-list-repeat;
      }
      container asn-lists {
        description
          "Action to prepend the specified multiple AS numbers to the AS path.";
        list asn-list {
          key "index";
            description
              "List of AS numbers to prepend to the AS path.";
          leaf index {
            type leafref {
              path "../config/index";
            }
            description
             "Reference to list key";
          }
          container config {
            description
              "Configuration data for AS numbers list for AS path
             prepend action";
            uses as-path-prepend-list;
          }
          container state {
            config false;
            description
              "Operation state data for AS numbers list for AS path
              prepend action";
            uses as-path-prepend-list;
          }
        }
      }
    }
    description
      "EOS allows to configure multiple AS number to prepend in AS path prepend.";
  }
}
