module arista-ale-counters-ipv4-prefix-counter-table {
  yang-version 1;
  namespace "http://arista.com/yang/experimental/eos/arista-ale-counters-ipv4-prefix-counter-table";
  prefix "arista-ale-counters-ipv4-prefix-counter-table";

  import openconfig-extensions { prefix "oc-ext"; }
  import openconfig-inet-types { prefix "openconfig-inet-types"; }
  organization
    "Arista Networks <http://arista.com/>";
  contact
    "Arista Networks <http://arista.com/>";
  description
    "This is the module for ipv4 prefix counter export types

    THIS YANG MODULE WAS GENERATED. DO NOT EDIT THIS FILE.";

  oc-ext:openconfig-version "1.0.0";

  revision "2022-05-03" {
    description
      "Version 1.0.0, generated on 2022-05-03";
    reference "1.0.0";
  }

  // covered-by: openconfig-network-instance.yang
  grouping prefix-counters {
    leaf packets-forwarded {
      type uint64;
      description
        "";
    }
    leaf octets-forwarded {
      type uint64;
      description
        "";
    }
    leaf packets-forwarded-backup {
      type uint64;
      description
        "";
    }
    leaf octets-forwarded-backup {
      type uint64;
      description
        "";
    }
    description
      "";
  }
  grouping state {
    container counters {
      uses prefix-counters;
      description
        "";
    }
    description
      "";
  }
  grouping ipv4-entry {
    leaf prefix {
      type openconfig-inet-types:ipv4-prefix;
      description
        "";
    }
    container state {
      uses state;
      description
        "";
    }
    description
      "";
  }
  grouping vrf {
    list ipv4-entry {
      key "prefix";
      uses ipv4-entry;
      description
        "";
    }
    description
      "";
  }
  grouping prefix-counters-table {
    list vrfs {
      key "name";
      uses vrf;
      description
        "";
    }
    leaf name {
      type string;
      description
        "name of the grouping";
    }
    description
      "";
  }
  container network-instances {
    list network-instance {
      key "name";
      leaf name {
        type string;
        description
          "name leaf used as key for network-instance list";
      }
      container afts {
        container ipv4-unicast {
          config false;
     uses vrf;
     description
         "ipv4-unicast container";
      }
        description
         "afts container";
      }
        description
         "network-instance list";
      }
        description
         "network-instances container";
      }
   }
