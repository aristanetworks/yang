module arista-arnet-conn-tuple {
  yang-version 1;
  namespace "http://arista.com/yang/experimental/eos/arista-arnet-conn-tuple";
  prefix "arista-arnet-conn-tuple";

  import openconfig-extensions { prefix "oc-ext"; }
  import arista-arnet-ip { prefix "arista-arnet-ip"; }
  import openconfig-packet-match-types { prefix "openconfig-packet-match-types"; }
  organization
    "Arista Networks <http://arista.com/>";
  contact
    "Arista Networks <http://arista.com/>";
  description
    "Yang model for connection tuple.

    THIS YANG MODULE WAS GENERATED. DO NOT EDIT THIS FILE.";

  oc-ext:openconfig-version "0.1.0";

  revision "2022-03-28" {
    description
      "Version 0.1.0, generated on 2022-03-28";
    reference "0.1.0";
  }

  grouping conn-tuple {
    container src-addr {
      uses arista-arnet-ip:ip-and-port;
      description
        "Source of the connection.";
    }
    container dst-addr {
      uses arista-arnet-ip:ip-and-port;
      description
        "Destination of the connection.";
    }
    leaf proto {
      type openconfig-packet-match-types:ip-protocol-type;
      description
        "IP Protocol used by the connection.";
    }
    description
      "Tuple to store information of the connection.";
  }
}
