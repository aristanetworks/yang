module openconfig-if-sdn-ext {
  yang-version "1";

  namespace "http://openconfig.net/interfaces/sdn-ext";
  prefix "oc-if-sdn";

  import openconfig-extensions { prefix oc-ext; }
  import openconfig-interfaces { prefix oc-if; }

  description
    "This module provides extensions to the OpenConfig interfaces
    module for network elements that support external 'SDN' control
    of their interfaces.";

  oc-ext:catalog-organization "openconfig";
  oc-ext:origin "openconfig";

  oc-ext:openconfig-version "0.1.0";

  revision 2021-03-30 {
    description
      "Initial revision.";
    reference "0.1.0";
  }

  grouping sdn-interface-config {
    description
      "Configuration parameters applicable to interfaces on devices
      that support SDN control.";

    leaf forwarding-viable {
      type boolean;
      default true;
      description
        "This value indicates whether the interface may be used
        to route traffic or not.  If set to false, the
        interface is not used for forwarding traffic, but as long as
        it is up, the interface still maintains its layer-2
        adjacencies and runs its configured layer-2 functions
        (e.g., LLDP, etc.).
        This is used by an external programming entity to disable an interface
        (usually part of an aggregate) for the purposes of forwarding
        traffic. This allows a logical aggregate to continue to be
        used with partial capacity, for example.  Note that setting
        `forwarding-viable = false` is not equivalent to
        administratively disabling the interface -- in particular, the
        interface is expected to participate in L2 protocols such as
        LLDP or LACP even if it blocked from forwarding traffic.";
    }
  }

  augment "/oc-if:interfaces/oc-if:interface/oc-if:config" {
    description
      "Add SDN extensions to interface intended configuration.";
    uses sdn-interface-config;
  }

  augment "/oc-if:interfaces/oc-if:interface/oc-if:state" {
    description
      "Add SDN extensions to interface applied configuration.";
    uses sdn-interface-config;
  }
}
