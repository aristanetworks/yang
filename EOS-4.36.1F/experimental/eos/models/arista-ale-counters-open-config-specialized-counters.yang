module arista-ale-counters-open-config-specialized-counters {
  yang-version 1;
  namespace "http://arista.com/yang/experimental/eos/arista-ale-counters-open-config-specialized-counters";
  prefix "arista-ale-counters-open-config-specialized-counters";
  
  import openconfig-extensions { prefix "oc-ext"; }
  import openconfig-platform { prefix "openconfig-platform"; }
  
  organization
    "Arista Networks <http://arista.com/>";
  contact
    "Arista Networks <http://arista.com/>";
  
  description
    "Specialized counters
    THIS YANG MODULE WAS GENERATED. DO NOT EDIT THIS FILE.";
  
  oc-ext:openconfig-version "1.0.0";
  
  revision "2021-10-20" {
    description
      "Version 1.0.0, generated on 2021-10-20";
    reference "1.0.0";
  }
  grouping ale-counters-open-config-specialized-counter {
    leaf name {
      type string;
      description
        "counter name";
    }
    leaf value {
      type uint64;
      description
        "value";
    }
    description
      "counter information";
  }
  grouping ale-counters-open-config-specialized-counters {
    leaf name {
      type string;
      description
        "name of the grouping";
    }
    list counter {
      key "name";
      uses ale-counters-open-config-specialized-counter;
      description
        "Container for Sand specific specialized counters.";
    }
    description
      "unused";
  }
  grouping ale-counters-open-config-specialized {
    leaf name {
      type string;
      description
        "name of the grouping";
    }
    description
      "";
  }
  augment "/openconfig-platform:components/openconfig-platform:component/openconfig-platform:integrated-circuit" {
    container specialized-counters {
      container vendor {
        container arista {
          container sand {
            uses ale-counters-open-config-specialized-counters;
            config false;
            description
              "sand container";
          }
          description
            "arista container";
        }
        description
          "vendor container";
      }
      description
        "specialized-counters container";
    }
  }
} // main-yang
