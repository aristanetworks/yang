module arista-traffic-policy {
  yang-version 1;
  namespace "http://arista.com/yang/experimental/eos/arista-traffic-policy";
  prefix "arista-traffic-policy";

  import openconfig-extensions { prefix "oc-ext"; }
  import arista-exp-eos { prefix "arista-exp-eos"; }
  organization
    "Arista Networks <http://arista.com/>";
  contact
    "Arista Networks <http://arista.com/>";
  description
    "Interface traffic policy counters

  This root yang module exists because traffic-policy container should only be augmented once.";

  oc-ext:openconfig-version "1.1.0";

  revision "2026-02-02" {
    description
      "Version 1.1.0, with control-plane-ingress-counters manually added";
    reference "1.1.0";
  }

  revision "2024-03-15" {
    description
      "Version 1.0.0, generated by AYG, manually trimmed away internal groupings/leaves";
    reference "1.0.0";
  }

  grouping traffic-policy-counter-data {
    leaf name {
      type string;
      description
        "Name of the counter";
    }
    leaf matched-packets {
      type uint64;
      description
        "Number of packets matched";
    }
    leaf dropped-packets {
      type uint64;
      description
        "Number of packets dropped";
    }
    leaf matched-octets {
      type uint64;
      description
        "Number of octets matched";
    }
    leaf dropped-octets {
      type uint64;
      description
        "Number of octets dropped";
    }
    description
      "Container for counters";
  }
  augment "/arista-exp-eos:arista" {
    container traffic-policy {
      container policies {
        list policy {
          key "name";
          leaf name {
            type string;
            description
              "name leaf used as key for policy list";
          }
          container control-plane-ingress-counters {
            list counter {
              key "name";
              leaf name {
                type string;
                description
                  "name leaf used as key for counter list";
              }
              container state {
                config false;
                uses traffic-policy-counter-data;
                description
                  "state container";
              }
              description
                "counter list";
            }
            description
              "control-plane-ingress-counters container";
          }
          container data-plane-egress-counters {
            list counter {
              key "name";
              leaf name {
                type string;
                description
                  "name leaf used as key for counter list";
              }
              container state {
                config false;
                uses traffic-policy-counter-data;
                description
                  "state container";
              }
              description
                "counter list";
            }
            description
              "data-plane-egress-counters container";
          }
          container data-plane-ingress-counters {
            list counter {
              key "name";
              leaf name {
                type string;
                description
                  "name leaf used as key for counter list";
              }
              container state {
                config false;
                uses traffic-policy-counter-data;
                description
                  "state container";
              }
              description
                "counter list";
            }
            description
              "data-plane-ingress-counters container";
          }
          description
            "policy list";
        }
        description
          "policies container";
      }
      description
        "traffic-policy container";
    }
    description
      "/arista-exp-eos:arista augment";
  }
}
