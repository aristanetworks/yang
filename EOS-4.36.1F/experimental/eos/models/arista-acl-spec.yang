module arista-acl-spec {
  yang-version 1;
  namespace "http://arista.com/yang/experimental/eos/arista-acl-spec";
  prefix "arista-acl-spec";
  
  import openconfig-extensions { prefix "oc-ext"; }
  
  organization
    "Arista Networks <http://arista.com/>";
  contact
    "Arista Networks <http://arista.com/>";
  
  description
    "Yang model for ACL specificities.
    THIS YANG MODULE WAS GENERATED. DO NOT EDIT THIS FILE.";
  
  oc-ext:openconfig-version "0.1.0";
  
  revision "2022-03-28" {
    description
      "Version 0.1.0, generated on 2022-03-28";
    reference "0.1.0";
  }
  typedef acl-range-operator {
    type enumeration {
      enum ANY {
        value 0;
        description
          "Match any.";
      }
      enum EQ {
        value 1;
        description
          "Match exactly.";
      }
      enum GT {
        value 2;
        description
          "Match greater than.";
      }
      enum LT {
        value 3;
        description
          "Match lesser than.";
      }
      enum NEQ {
        value 4;
        description
          "Match different.";
      }
      enum RANGE {
        value 5;
        description
          "Match a specific range.";
      }
    }
    description
      "Range of a rule.";
  }
  grouping acl-port-spec {
    leaf oper {
      type acl-range-operator;
      description
        "Specify how to match the specified port.";
    }
    leaf ports {
      type string;
      description
        "Whitespace separated list of port to be used by the ACL.";
    }
    description
      "Specific port matched by an ACL.";
  }
} // main-yang
