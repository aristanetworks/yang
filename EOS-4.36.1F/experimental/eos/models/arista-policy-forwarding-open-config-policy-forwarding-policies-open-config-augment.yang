module arista-policy-forwarding-open-config-policy-forwarding-policies-open-config-augment {
  yang-version 1;
  namespace "http://arista.com/yang/arista-policy-forwarding-open-config-policy-forwarding-policies-open-config-augment";
  prefix "arista-policy-forwarding-open-config-policy-forwarding-policies-open-config-augment";
  
  import openconfig-extensions { prefix "oc-ext"; }
  import openconfig-acl { prefix "openconfig-acl"; }
  import openconfig-icmpv4-types { prefix "openconfig-icmpv4-types"; }
  import openconfig-icmpv6-types { prefix "openconfig-icmpv6-types"; }
  import openconfig-inet-types { prefix "openconfig-inet-types"; }
  import openconfig-network-instance { prefix "openconfig-network-instance"; }
  import openconfig-packet-match-types { prefix "openconfig-packet-match-types"; }
  import openconfig-yang-types { prefix "openconfig-yang-types"; }
  
  organization
    "Arista Networks <http://arista.com/>";
  contact
    "Arista Networks <http://arista.com/>";
  
  description
    "This is the model for policy forwarding model
    THIS YANG MODULE WAS GENERATED. DO NOT EDIT THIS FILE.";
  
  oc-ext:openconfig-version "1.0.0";
  
  revision "2025-04-22" {
    description
      "Version 1.0.0, generated on 2025-04-22";
    reference "1.0.0";
  }
  grouping policy-forwarding-open-config-pf-policy-rule-action-config {
    leaf count {
      type boolean;
      description
        "Add a counter on a rule";
    }
    description
      "policy-forwarding-open-config-pf-policy-rule-action-config";
  }
  augment "/openconfig-network-instance:network-instances/openconfig-network-instance:network-instance/openconfig-network-instance:policy-forwarding/openconfig-network-instance:policies/openconfig-network-instance:policy/openconfig-network-instance:rules/openconfig-network-instance:rule/openconfig-network-instance:action/openconfig-network-instance:config" {
    leaf count {
      type boolean;
      description
        "Add a counter on a rule";
    }
    description
      "counter";
  }
  augment "/openconfig-network-instance:network-instances/openconfig-network-instance:network-instance/openconfig-network-instance:policy-forwarding/openconfig-network-instance:policies/openconfig-network-instance:policy/openconfig-network-instance:rules/openconfig-network-instance:rule/openconfig-network-instance:action/openconfig-network-instance:state" {
    leaf count {
      type boolean;
      description
        "Add a counter on a rule";
    }
    description
      "counter";
  }
} // augment-yang
