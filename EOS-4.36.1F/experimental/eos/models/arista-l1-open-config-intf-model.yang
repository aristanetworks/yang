module arista-l1-open-config-intf-model {
  yang-version 1;
  namespace "http://arista.com/yang/experimental/eos/arista-l1-open-config-intf-model";
  prefix "arista-l1-open-config-intf-model";
  
  import openconfig-extensions { prefix "oc-ext"; }
  import arista-ebra-sub-intf { prefix "arista-ebra-sub-intf"; }
  import openconfig-interfaces { prefix "openconfig-interfaces"; }
  
  organization
    "Arista Networks <http://arista.com/>";
  contact
    "Arista Networks <http://arista.com/>";
  
  description
    "Attributes related to interfaces
    THIS YANG MODULE WAS GENERATED. DO NOT EDIT THIS FILE.";
  
  oc-ext:openconfig-version "1.0.0";
  
  revision "2025-09-03" {
    description
      "Version 1.0.0, generated on 2025-09-03";
    reference "1.0.0";
  }
  typedef l1-open-config-interface-ext-op-status {
    type enumeration {
      enum UNKNOWN {
        value 0;
        description
          "unknown";
      }
      enum CONNECTED {
        value 1;
        description
          "Interface is operable and the physical link is up";
      }
      enum NOTCONNECT {
        value 2;
        description
          "Interface is operable but the physical link is down ";
      }
      enum INACTIVE {
        value 3;
        description
          "Interface is inoperable due to hardware restrictions";
      }
      enum NO_RESOURCE {
        value 4;
        description
          "Interface is inoperable due to insufficient hardware resources";
      }
      enum ERRDISABLED {
        value 5;
        description
          "Interface is inoperable due to a configuration or runtime error";
      }
      enum MAINT_DOWN {
        value 6;
        description
          "Interface is inoperable due to maintenance";
      }
      enum INITIALIZING {
        value 7;
        description
          "Interface is inoperable because the system is initializing";
      }
      enum DISABLED {
        value 8;
        description
          "Interface is inoperable due to being administratively shut down";
      }
      enum ISOLATED {
        value 9;
        description
          "Interface is operable but cannot be used for traffic";
      }
    }
    description
      "Extended operational status of an interface";
  }
  grouping l1-open-config-interface-reason-detail {
    leaf index {
      type uint32;
      description
        "index";
    }
    leaf code {
      type string;
      description
        "code";
    }
    leaf detail {
      type string;
      description
        "detailed explanation";
    }
    description
      "A Reason and its corresponding explanation to the extended operational status of an interface";
  }
  grouping l1-open-config-interface-sub-intf-status-detail {
    uses arista-ebra-sub-intf:interface-sub-intf-key;
    description
      "Attributes for the extended operational status of a sub-interface";
  }
  grouping l1-open-config-interface-intf-status-detail {
    leaf intf-name {
      type string;
      description
        "The interface name (eg, EthernetX/Y)";
    }
    description
      "Attributes for the extended operational status of an interface";
  }
  grouping l1-open-config-interface-intf-status-detail-container {
    list intf-status-detail {
      key "intf-name";
      uses l1-open-config-interface-intf-status-detail;
      description
        "The state container for extended interface operational status";
    }
    list sub-intf-status-detail {
      key "parent-intf-name index";
      uses l1-open-config-interface-sub-intf-status-detail;
      description
        "The state container for extended sub-interface operational status";
    }
    description
      "Container for the extended interface operational status component";
  }
  augment "/openconfig-interfaces:interfaces/openconfig-interfaces:interface" {
    container extended-oper-status {
      container state {
        leaf status {
          config false;
          type l1-open-config-interface-ext-op-status;
          description
            "extended operational status";
        }
        description
          "state container";
      }
      container reasons {
        list reason {
          key "index";
          leaf index {
            type uint32;
            description
              "index leaf used as key for reason list";
          }
          container state {
            uses l1-open-config-interface-reason-detail;
            config false;
            description
              "state container";
          }
          description
            "reason list";
        }
        description
          "reasons container";
      }
      description
        "extended-oper-status container";
    }
  }
  augment "/openconfig-interfaces:interfaces/openconfig-interfaces:interface/openconfig-interfaces:subinterfaces/openconfig-interfaces:subinterface" {
    container extended-oper-status {
      container state {
        leaf status {
          config false;
          type l1-open-config-interface-ext-op-status;
          description
            "extended operational status";
        }
        description
          "state container";
      }
      container reasons {
        list reason {
          key "index";
          leaf index {
            type uint32;
            description
              "index leaf used as key for reason list";
          }
          container state {
            uses l1-open-config-interface-reason-detail;
            config false;
            description
              "state container";
          }
          description
            "reason list";
        }
        description
          "reasons container";
      }
      description
        "extended-oper-status container";
    }
  }
} // main-yang
