module arista-bgp-common-bgp-open-config-global-lbw-options {
  yang-version 1;
  namespace "http://arista.com/yang/experimental/eos/arista-bgp-common-bgp-open-config-global-lbw-options";
  prefix "arista-bgp-common-bgp-open-config-global-lbw-options";
  
  import openconfig-extensions { prefix "oc-ext"; }
  import openconfig-network-instance { prefix "openconfig-network-instance"; }
  
  organization
    "Arista Networks <http://arista.com/>";
  contact
    "Arista Networks <http://arista.com/>";
  
  description
    "Support for BGP Global Link Bandwidth Options
    THIS YANG MODULE WAS GENERATED. DO NOT EDIT THIS FILE.";
  
  oc-ext:openconfig-version "1.0.0";
  
  revision "2026-02-02" {
    description
      "Version 1.0.0, generated on 2026-02-02";
    reference "1.0.0";
  }
  grouping routing-bgp-open-config-link-bandwidth-export-config {
    leaf regen-limit-enabled {
      type boolean;
      description
        "Limit the advertised link-bandwidth value such that it does not exceed the speed of the interface over which the advertisement is being sent. If set to false, the limiting action will be disabled.";
    }
    description
      "Configuration data for link-bandwidth export options";
  }
  grouping routing-bgp-open-config-link-bandwidth-export {
    container config {
      uses routing-bgp-open-config-link-bandwidth-export-config;
      description
        "Configuration data for link-bandwidth export options";
    }
    container state {
      uses routing-bgp-open-config-link-bandwidth-export-config;
      config false;
      description
        "Operational state data for link-bandwidth export options";
    }
    description
      "Outbound link-bandwidth signaling policies.
      These settings determine how the local system populates or
      modifies the link-bandwidth extended community before sending
      updates to BGP peer.";
  }
  grouping routing-bgp-open-config-link-bandwidth-options {
    container export {
      uses routing-bgp-open-config-link-bandwidth-export;
      description
        "Container used to provide configuration and state
        parameters related to outbound processing of various
        link-bandwidth options";
    }
    description
      "Configuration parameters related to the BGP Link-Bandwidth
      extended community. These options control how bandwidth
      values are calculated, modified, and advertised to peers.";
  }
  augment "/openconfig-network-instance:network-instances/openconfig-network-instance:network-instance/openconfig-network-instance:protocols/openconfig-network-instance:protocol/openconfig-network-instance:bgp/openconfig-network-instance:global" {
    container link-bandwidth-options {
      uses routing-bgp-open-config-link-bandwidth-options;
      description
        "link-bandwidth-options container";
    }
  }
} // main-yang
