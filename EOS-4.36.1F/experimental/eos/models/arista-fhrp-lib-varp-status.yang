module arista-fhrp-lib-varp-status {
  yang-version 1;
  namespace "http://arista.com/yang/experimental/eos/arista-fhrp-lib-varp-status";
  prefix "arista-fhrp-lib-varp-status";
  
  import openconfig-extensions { prefix "oc-ext"; }
  import arista-exp-eos { prefix "arista-exp-eos"; }
  import arista-fhrp-fhrp-config { prefix "arista-fhrp-fhrp-config"; }
  import openconfig-inet-types { prefix "openconfig-inet-types"; }
  import openconfig-interfaces { prefix "openconfig-interfaces"; }
  
  organization
    "Arista Networks <http://arista.com/>";
  contact
    "Arista Networks <http://arista.com/>";
  
  description
    "Status for virtual rounter IP addresses
    THIS YANG MODULE WAS GENERATED. DO NOT EDIT THIS FILE.";
  
  oc-ext:openconfig-version "1.0.0";
  
  revision "2023-03-13" {
    description
      "Version 1.0.0, generated on 2023-03-13";
    reference "1.0.0";
  }
  grouping routing-fhrp-varp-intf-status-v4 {
    leaf intf-id {
      type openconfig-interfaces:interface-id;
      description
        "Interface identifier";
    }
    list virtual-ip-addr {
      key "virtual-ip-addr-key";
      leaf virtual-ip-addr-key {
        type openconfig-inet-types:ipv4-address;
        description
          "openconfig-inet-types:ipv4-address key for virtual-ip-addr list.";
      }
      description
        "List of IPv4 virtual router addresses";
    }
    description
      "VARP IPv4 status per interface";
  }
  grouping routing-fhrp-varp-intf-status-v6 {
    leaf intf-id {
      type openconfig-interfaces:interface-id;
      description
        "Interface identifier";
    }
    list virtual-ip6-addr {
      key "virtual-ip6-addr-key";
      leaf virtual-ip6-addr-key {
        type openconfig-inet-types:ipv6-address;
        description
          "openconfig-inet-types:ipv6-address key for virtual-ip6-addr list.";
      }
      description
        "List of IPv6 virtual router addresses";
    }
    description
      "VARP IPv6 status per interface";
  }
  grouping routing-fhrp-varp-status {
    list varp-intf-status-v4 {
      key "intf-id";
      uses routing-fhrp-varp-intf-status-v4;
      description
        "VARP IPv4 status";
    }
    list varp-intf-status-v6 {
      key "intf-id";
      uses routing-fhrp-varp-intf-status-v6;
      description
        "VARP IPv6 status";
    }
    description
      "Status data for VARP";
  }
  augment "/arista-exp-eos:arista/arista-fhrp-fhrp-config:varp" {
    container status {
      uses routing-fhrp-varp-status;
      config false;
      description
        "status container";
    }
  }
} // main-yang
