module arista-bfd-open-config-session-config {
  yang-version 1;
  namespace "http://arista.com/yang/experimental/eos/arista-bfd-open-config-session-config";
  prefix "arista-bfd-open-config-session-config";
  
  import openconfig-extensions { prefix "oc-ext"; }
  import openconfig-bfd { prefix "openconfig-bfd"; }
  import openconfig-inet-types { prefix "openconfig-inet-types"; }
  import openconfig-interfaces { prefix "openconfig-interfaces"; }
  
  organization
    "Arista Networks <http://arista.com/>";
  contact
    "Arista Networks <http://arista.com/>";
  
  description
    "Bfd session config
    THIS YANG MODULE WAS GENERATED. DO NOT EDIT THIS FILE.";
  
  oc-ext:openconfig-version "1.0.0";
  
  revision "2024-11-12" {
    description
      "Version 1.0.0, generated on 2024-11-12";
    reference "1.0.0";
  }
  grouping bfd-ocbfd-session-key {
    leaf intf-id {
      type openconfig-interfaces:interface-id;
      description
        "";
    }
    leaf remote-address {
      type openconfig-inet-types:ip-address;
      description
        "";
    }
    description
      "";
  }
  grouping bfd-ocbfd-session {
    leaf remote-address {
      type openconfig-inet-types:ip-address;
      description
        "The remote IP destination that should be used by the system for the single-hop BFD session specified.";
    }
    description
      "";
  }
  grouping bfd-ocbfd-session-elem {
    uses bfd-ocbfd-session-key;
    container config {
      uses bfd-ocbfd-session;
      description
        "Configuration parameters for the static BFD single-hop session.";
    }
    description
      "";
  }
  grouping bfd-ocbfd-session-config {
    leaf name {
      type string;
      description
        "name of the grouping";
    }
    description
      "Structural grouping for static BFD single-hop sessions configuration on interface and state parameters.";
  }
  augment "/openconfig-bfd:bfd/openconfig-bfd:interfaces/openconfig-bfd:interface" {
    container sessions {
      list session {
        key "remote-address";
        uses bfd-ocbfd-session-elem;
        description
          "session list";
      }
      description
        "sessions container";
    }
  }
} // main-yang
