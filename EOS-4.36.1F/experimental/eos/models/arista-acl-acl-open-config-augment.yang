module arista-acl-acl-open-config-augment {
  yang-version 1;
  namespace "http://arista.com/yang/arista-acl-acl-open-config-augment";
  prefix "arista-acl-acl-open-config-augment";
  
  import openconfig-extensions { prefix "oc-ext"; }
  import arista-arnet-vrf-name { prefix "arista-arnet-vrf-name"; }
  import openconfig-acl { prefix "openconfig-acl"; }
  import openconfig-icmpv4-types { prefix "openconfig-icmpv4-types"; }
  import openconfig-icmpv6-types { prefix "openconfig-icmpv6-types"; }
  import openconfig-inet-types { prefix "openconfig-inet-types"; }
  import openconfig-packet-match-types { prefix "openconfig-packet-match-types"; }
  import openconfig-yang-types { prefix "openconfig-yang-types"; }
  
  organization
    "Arista Networks <http://arista.com/>";
  contact
    "Arista Networks <http://arista.com/>";
  
  description
    "External tac model for traffic policy
    THIS YANG MODULE WAS GENERATED. DO NOT EDIT THIS FILE.";
  
  oc-ext:openconfig-version "1.1.0";
  
  revision "2025-08-15" {
    description
      "Version 1.1.0, generated on 2025-08-15";
    reference "1.1.0";
  }
  typedef acl-open-config-counter-action {
    type enumeration {
      enum COUNT_NONE {
        value 0;
        description
          "No counter for the acl-entry ";
      }
      enum COUNT {
        value 1;
        description
          "Counter enabled for the acl-entry ";
      }
    }
    description
      "acl-open-config-counter-action";
  }
  typedef acl-open-config-oc-acl-cpu-ip-traffic {
    type enumeration {
      enum UNICAST {
        value 0;
        description
          "Match on unicast traffic destined to CPU";
      }
    }
    description
      "Traffic Policy match on CPU traffic options";
  }
  typedef acl-open-config-oc-acl-prefix-match-mode {
    type enumeration {
      enum ORDERED {
        value 0;
        description
          "Ordered by sequence-id";
      }
      enum LPM {
        value 1;
        description
          "Longest Prefix Match";
      }
    }
    description
      "Traffic Policy prefix match mode";
  }
  typedef acl-open-config-ocacl-mode {
    type enumeration {
      enum STATIC {
        value 0;
        description
          "Traffic policy config is added to the running-config";
      }
      enum CONTROLLER {
        value 1;
        description
          "Traffic Policy config populated by controller that isnon-persistent across reloads";
      }
    }
    description
      "Traffic Policy config mode";
  }
  grouping acl-open-config-ocacl-ip-common-config {
    leaf cpu-traffic {
      type acl-open-config-oc-acl-cpu-ip-traffic;
      description
        "Match on traffic destined to CPU";
    }
    description
      "acl-open-config-ocacl-ip-common-config";
  }
  grouping acl-open-config-ocacl-transport-config {
    leaf-list source-port-list {
      type openconfig-packet-match-types:port-num-range;
      oc-ext:telemetry-atomic;
      description
        "List of oc-pkt-match-types:port-num-range to match the source port";
    }
    leaf-list destination-port-list {
      type openconfig-packet-match-types:port-num-range;
      oc-ext:telemetry-atomic;
      description
        "List of oc-pkt-match-types:port-num-range to match the destination port";
    }
    description
      "acl-open-config-ocacl-transport-config";
  }
  grouping acl-open-config-counter {
    leaf count-action {
      type acl-open-config-counter-action;
      default COUNT_NONE;
      description
        "No counter for the acl-entry ";
    }
    description
      "Add a counter on an acl-entry ";
  }
  grouping acl-open-config-ocacl-actions-config {
    leaf-list next-hops {
      type openconfig-inet-types:ip-address;
      description
        "next-hops";
    }
    leaf next-hop-network-instance {
      type arista-arnet-vrf-name:l3-vrf-name;
      description
        "next-hop-network-instance";
    }
    leaf next-hop-recurse {
      type boolean;
      description
        "next-hop-recurse";
    }
    leaf ttl {
      type uint8;
      description
        "ttl";
    }
    description
      "acl-open-config-ocacl-actions-config";
  }
  grouping acl-open-config-ocacl-entry-config {
    leaf rule-name {
      type string;
      description
        "Traffic Policy rule name";
    }
    description
      "acl-open-config-ocacl-entry-config";
  }
  grouping acl-open-config-ocacl-set-config {
    leaf mode {
      type acl-open-config-ocacl-mode;
      default STATIC;
      description
        "mode";
    }
    description
      "acl-open-config-ocacl-set-config";
  }
  grouping acl-open-config-ocacl-config {
    leaf prefix-match-mode {
      type acl-open-config-oc-acl-prefix-match-mode;
      default ORDERED;
      description
        "prefix-match-mode";
    }
    description
      "acl-open-config-ocacl-config";
  }
  augment "/openconfig-acl:acl/openconfig-acl:acl-sets/openconfig-acl:acl-set/openconfig-acl:acl-entries/openconfig-acl:acl-entry/openconfig-acl:ipv4/openconfig-acl:config" {
    leaf cpu-traffic {
      type acl-open-config-oc-acl-cpu-ip-traffic;
      description
        "Match on traffic destined to CPU";
    }
    description
      "To CPU Traffic";
  }
  augment "/openconfig-acl:acl/openconfig-acl:acl-sets/openconfig-acl:acl-set/openconfig-acl:acl-entries/openconfig-acl:acl-entry/openconfig-acl:ipv4/openconfig-acl:state" {
    leaf cpu-traffic {
      type acl-open-config-oc-acl-cpu-ip-traffic;
      description
        "Match on traffic destined to CPU";
    }
    description
      "To CPU Traffic";
  }
  augment "/openconfig-acl:acl/openconfig-acl:acl-sets/openconfig-acl:acl-set/openconfig-acl:acl-entries/openconfig-acl:acl-entry/openconfig-acl:ipv6/openconfig-acl:config" {
    leaf cpu-traffic {
      type acl-open-config-oc-acl-cpu-ip-traffic;
      description
        "Match on traffic destined to CPU";
    }
    description
      "To CPU Traffic";
  }
  augment "/openconfig-acl:acl/openconfig-acl:acl-sets/openconfig-acl:acl-set/openconfig-acl:acl-entries/openconfig-acl:acl-entry/openconfig-acl:ipv6/openconfig-acl:state" {
    leaf cpu-traffic {
      type acl-open-config-oc-acl-cpu-ip-traffic;
      description
        "Match on traffic destined to CPU";
    }
    description
      "To CPU Traffic";
  }
  augment "/openconfig-acl:acl/openconfig-acl:acl-sets/openconfig-acl:acl-set/openconfig-acl:acl-entries/openconfig-acl:acl-entry/openconfig-acl:transport/openconfig-acl:config" {
    leaf-list source-port-list {
      type openconfig-packet-match-types:port-num-range;
      oc-ext:telemetry-atomic;
      description
        "List of oc-pkt-match-types:port-num-range to match the source port";
    }
    leaf-list destination-port-list {
      type openconfig-packet-match-types:port-num-range;
      oc-ext:telemetry-atomic;
      description
        "List of oc-pkt-match-types:port-num-range to match the destination port";
    }
    description
      "source port list
      destination port list";
  }
  augment "/openconfig-acl:acl/openconfig-acl:acl-sets/openconfig-acl:acl-set/openconfig-acl:acl-entries/openconfig-acl:acl-entry/openconfig-acl:transport/openconfig-acl:state" {
    leaf-list source-port-list {
      type openconfig-packet-match-types:port-num-range;
      oc-ext:telemetry-atomic;
      description
        "List of oc-pkt-match-types:port-num-range to match the source port";
    }
    leaf-list destination-port-list {
      type openconfig-packet-match-types:port-num-range;
      oc-ext:telemetry-atomic;
      description
        "List of oc-pkt-match-types:port-num-range to match the destination port";
    }
    description
      "source port list
      destination port list";
  }
  augment "/openconfig-acl:acl/openconfig-acl:acl-sets/openconfig-acl:acl-set/openconfig-acl:acl-entries/openconfig-acl:acl-entry/openconfig-acl:actions/openconfig-acl:config" {
    container counter {
      uses acl-open-config-counter;
      description
        "counter";
    }
    leaf-list next-hops {
      type openconfig-inet-types:ip-address;
      description
        "next-hops";
    }
    leaf next-hop-network-instance {
      type arista-arnet-vrf-name:l3-vrf-name;
      description
        "next-hop-network-instance";
    }
    leaf next-hop-recurse {
      type boolean;
      description
        "next-hop-recurse";
    }
    leaf ttl {
      type uint8;
      description
        "ttl";
    }
    description
      "counter
      Redirect next-hop list
      Vrf to resolve the nexthop in. If unspecified vrf from the
      policy application site is used
      Resolve next-hop using the longest prefix match
      Set time-to-live";
  }
  augment "/openconfig-acl:acl/openconfig-acl:acl-sets/openconfig-acl:acl-set/openconfig-acl:acl-entries/openconfig-acl:acl-entry/openconfig-acl:actions/openconfig-acl:state" {
    container counter {
      uses acl-open-config-counter;
      description
        "counter";
    }
    leaf-list next-hops {
      type openconfig-inet-types:ip-address;
      description
        "next-hops";
    }
    leaf next-hop-network-instance {
      type arista-arnet-vrf-name:l3-vrf-name;
      description
        "next-hop-network-instance";
    }
    leaf next-hop-recurse {
      type boolean;
      description
        "next-hop-recurse";
    }
    leaf ttl {
      type uint8;
      description
        "ttl";
    }
    description
      "counter
      Redirect next-hop list
      Vrf to resolve the nexthop in. If unspecified vrf from the
      policy application site is used
      Resolve next-hop using the longest prefix match
      Set time-to-live";
  }
  augment "/openconfig-acl:acl/openconfig-acl:acl-sets/openconfig-acl:acl-set/openconfig-acl:acl-entries/openconfig-acl:acl-entry/openconfig-acl:config" {
    leaf rule-name {
      type string;
      description
        "Traffic Policy rule name";
    }
    description
      "traffic-policy rule name";
  }
  augment "/openconfig-acl:acl/openconfig-acl:acl-sets/openconfig-acl:acl-set/openconfig-acl:acl-entries/openconfig-acl:acl-entry/openconfig-acl:state" {
    leaf rule-name {
      type string;
      description
        "Traffic Policy rule name";
    }
    description
      "traffic-policy rule name";
  }
  augment "/openconfig-acl:acl/openconfig-acl:acl-sets/openconfig-acl:acl-set/openconfig-acl:config" {
    leaf mode {
      type acl-open-config-ocacl-mode;
      default STATIC;
      description
        "mode";
    }
    description
      "traffic-policy mode";
  }
  augment "/openconfig-acl:acl/openconfig-acl:acl-sets/openconfig-acl:acl-set/openconfig-acl:state" {
    leaf mode {
      type acl-open-config-ocacl-mode;
      default STATIC;
      description
        "mode";
    }
    description
      "traffic-policy mode";
  }
  augment "/openconfig-acl:acl/openconfig-acl:config" {
    leaf prefix-match-mode {
      type acl-open-config-oc-acl-prefix-match-mode;
      default ORDERED;
      description
        "prefix-match-mode";
    }
    description
      "traffic-policy prefix match mode";
  }
} // augment-yang
