module arista-dhcp-relay-dhcp-relay-open-config-v4-augment {
  yang-version 1;
  namespace "http://arista.com/yang/arista-dhcp-relay-dhcp-relay-open-config-v4-augment";
  prefix "arista-dhcp-relay-dhcp-relay-open-config-v4-augment";
  
  import openconfig-extensions { prefix "oc-ext"; }
  import arista-arnet-vrf-name { prefix "arista-arnet-vrf-name"; }
  import openconfig-inet-types { prefix "openconfig-inet-types"; }
  import openconfig-interfaces { prefix "openconfig-interfaces"; }
  import openconfig-relay-agent { prefix "openconfig-relay-agent"; }
  
  organization
    "Arista Networks <http://arista.com/>";
  contact
    "Arista Networks <http://arista.com/>";
  
  description
    "Dhcp Relay Model
    THIS YANG MODULE WAS GENERATED. DO NOT EDIT THIS FILE.";
  
  oc-ext:openconfig-version "0.0.0";
  
  revision "2024-08-25" {
    description
      "Version 0.0.0, generated on 2024-08-25";
    reference "0.0.0";
  }
  typedef ip-helper-dhcp-relay-open-config-oc-dhcp-relay-local-address {
    type union {
      type openconfig-inet-types:ipv4-address;
      type openconfig-interfaces:interface-id;
    }
    description
      "ip-helper-dhcp-relay-open-config-oc-dhcp-relay-local-address";
  }
  typedef ip-helper-dhcp-relay-open-config-ocdhcp-relay-address {
    type union {
      type openconfig-inet-types:ipv4-address;
      type string;
    }
    description
      "ip-helper-dhcp-relay-open-config-ocdhcp-relay-address";
  }
  grouping ip-helper-dhcp-relay-open-config-ocdhcp-relay-address-vrf-pair {
    leaf address {
      type ip-helper-dhcp-relay-open-config-ocdhcp-relay-address;
      description
        "address";
    }
    leaf network-instance {
      type arista-arnet-vrf-name:l3-vrf-name;
      description
        "network-instance";
    }
    description
      "ip-helper-dhcp-relay-open-config-ocdhcp-relay-address-vrf-pair";
  }
  grouping ip-helper-dhcp-relay-open-config-ocdhcp-relay-intf-key {
    description
      "ip-helper-dhcp-relay-open-config-ocdhcp-relay-intf-key";
  }
  grouping ip-helper-dhcp-relay-open-config-oc-dhcp-relay-helper-address-config {
    container address-pair {
      uses ip-helper-dhcp-relay-open-config-ocdhcp-relay-address-vrf-pair;
      description
        "address-pair";
    }
    leaf source-address {
      type ip-helper-dhcp-relay-open-config-oc-dhcp-relay-local-address;
      description
        "source-address";
    }
    description
      "ip-helper-dhcp-relay-open-config-oc-dhcp-relay-helper-address-config";
  }
  grouping ip-helper-dhcp-relay-open-config-oc-dhcp-relay-helper-address {
    uses ip-helper-dhcp-relay-open-config-ocdhcp-relay-address-vrf-pair;
    container config {
      uses ip-helper-dhcp-relay-open-config-oc-dhcp-relay-helper-address-config;
      description
        "config";
    }
    container state {
      uses ip-helper-dhcp-relay-open-config-oc-dhcp-relay-helper-address-config;
      config false;
      description
        "state";
    }
    description
      "ip-helper-dhcp-relay-open-config-oc-dhcp-relay-helper-address";
  }
  grouping ip-helper-dhcp-relay-open-config-oc-dhcp-relay-helper-addresses {
    list helper-address {
      key "address network-instance";
      uses ip-helper-dhcp-relay-open-config-oc-dhcp-relay-helper-address;
      description
        "helper-address";
    }
    description
      "ip-helper-dhcp-relay-open-config-oc-dhcp-relay-helper-addresses";
  }
  grouping ip-helper-dhcp-relay-open-config-interface-ref-config {
    description
      "ip-helper-dhcp-relay-open-config-interface-ref-config";
  }
  grouping ip-helper-dhcp-relay-open-config-interface-ref {
    description
      "ip-helper-dhcp-relay-open-config-interface-ref";
  }
  grouping ip-helper-dhcp-relay-open-config-interface-config {
    description
      "ip-helper-dhcp-relay-open-config-interface-config";
  }
  grouping ip-helper-dhcp-relay-open-config-ocdhcp-relay-intf {
    uses ip-helper-dhcp-relay-open-config-ocdhcp-relay-intf-key;
    description
      "ip-helper-dhcp-relay-open-config-ocdhcp-relay-intf";
  }
  augment "/openconfig-relay-agent:relay-agent/openconfig-relay-agent:dhcp/openconfig-relay-agent:interfaces/openconfig-relay-agent:interface" {
    container helper-addresses {
      uses ip-helper-dhcp-relay-open-config-oc-dhcp-relay-helper-addresses;
      description
        "helper-addresses";
    }
    description
      "relayAddressesAugment";
  }
} // augment-yang
