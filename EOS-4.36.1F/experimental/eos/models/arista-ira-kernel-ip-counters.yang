module arista-ira-kernel-ip-counters {
  yang-version 1;
  namespace "http://arista.com/yang/experimental/eos/arista-ira-kernel-ip-counters";
  prefix "arista-ira-kernel-ip-counters";
  
  import openconfig-extensions { prefix "oc-ext"; }
  import openconfig-network-instance { prefix "openconfig-network-instance"; }
  
  organization
    "Arista Networks <http://arista.com/>";
  contact
    "Arista Networks <http://arista.com/>";
  
  description
    "Aggregated kernel ip counters
    THIS YANG MODULE WAS GENERATED. DO NOT EDIT THIS FILE.";
  
  oc-ext:openconfig-version "1.0.0";
  
  revision "2025-02-18" {
    description
      "Version 1.0.0, generated on 2025-02-18";
    reference "1.0.0";
  }
  typedef ira-open-config-forwarding-type {
    type enumeration {
      enum FORWARDING {
        value 1;
        description
          "Entity is acting as a gateway and forwards datagrams.";
      }
      enum NOTFORWARDING {
        value 2;
        description
          "Entity is NOT acting as a gateway and does not forward datagrams.";
      }
    }
    description
      "The indication of whether this entity is acting as an IP gateway in respect to the forwarding of datagrams received by, but not addressed to, this entity. Reference: RFC1213 Section 6 ipForwarding";
  }
  grouping ira-open-config-ip-counters {
    leaf forwarding {
      type ira-open-config-forwarding-type;
      description
        "The indication of whether this entity is acting as an IPv4 gateway in respect to the forwarding of datagrams received by, but not addressed to, this entity. IPv4 gateways forward datagrams; Hosts do not (except those Source-Routed via the host). Reference: RFC1213 Section 6 ipForwarding";
    }
    leaf default-ttl {
      type uint8;
      description
        "The default value inserted into the Time-To-Live field of the IPv4 header of datagrams originated at this entity, whenever a TTL value is not supplied by the transport layer protocol. Reference: RFC1213 Section 6 ipDefaultTtl";
    }
    leaf in-receives {
      type uint64;
      description
        "The total number of input IPv4 datagrams received frominterfaces, including those received in error. Reference: RFC1213 Section 6 ipInReceives";
    }
    leaf in-header-errors {
      type uint64;
      description
        "The number of input datagrams discarded due to errors in their IPv4 headers, including bad checksums, version number mismatch, other format errors, time-to-live exceeded, errors discovered in processing their IPv4 options, etc. Reference: RFC1213 Section 6 ipInHdrErrors";
    }
    leaf in-address-errors {
      type uint64;
      description
        "The number of input datagrams discarded because the IPv4 address in their IPv4 header's destination field was not a valid address to be received at this entity. This count includes invalid addresses (e.g., 0.0.0.0) and addresses of unsupported Classes (e.g., Class E). For entities which are not IPv4 Gateways and therefore do not forward datagrams, this counter includes datagrams discarded because the destination address was not a local address. Reference: RFC1213 Section 6 ipInAddrErrors";
    }
    leaf in-forwarded-datagrams {
      type uint64;
      description
        "The number of input datagrams for which this entity was not their final IPv4 destination, as a result of which an attempt was made to find a route to forward them to that final destination. In entities which do not act as IPv4 routers, this counter will include only those packets which were Source-Routed via this entity, and the Source-Route option processing was successful. Reference: RFC1213 Section 6 ipForwDatagrams";
    }
    leaf in-unknown-protos {
      type uint64;
      description
        "The number of locally-addressed datagrams received successfully but discarded because of an unknown or unsupported protocol. Reference: RFC1213 Section 6 ipInUnknownProtos";
    }
    leaf in-discards {
      type uint64;
      description
        "The number of input IPv4 datagrams for which no problems were encountered to prevent their continued processing, but which were discarded (e.g., for lack of buffer space). Note that this counter does not include any datagrams discarded while awaiting re-assembly. Reference: RFC1213 Section 6 ipInDiscards";
    }
    leaf in-delivers {
      type uint64;
      description
        "The total number of input datagrams successfully delivered to IPv4 user-protocols (including ICMP). Reference: RFC1213 Section 6 ipInDelivers";
    }
    leaf out-requests {
      type uint64;
      description
        "The total number of IPv4 datagrams which local IPv4 user protocols (including ICMP) supplied to IPv4 in requests for transmission. Note that this counter does not include any datagrams counted in in-forwarded-datagrams. Reference: RFC1213 Section 6 ipOutRequests";
    }
    leaf out-discards {
      type uint64;
      description
        "The number of outbound packets which were chosen to be discarded even though no errors had been detected to prevent their being transmitted. One possible reason for discarding such a packet could be to free up buffer space. Reference: RFC1213 Section 6 ipOutDiscards";
    }
    leaf out-no-routes {
      type uint64;
      description
        "The number of IPv4 datagrams discarded because no route could be found to transmit them to their destination. Note that this counter includes any packets counted in in-forwarded-datagrams which meet this 'no-route' criterion. Note that this includes any datagrams which a host cannot route because all of its default routers are down. Reference: RFC1213 Section 6 ipOutNoRoutes";
    }
    leaf reassembly-timeout {
      type uint64;
      description
        "The maximum number of seconds which received fragments are held while they are awaiting reassembly at this entity. Reference: RFC1213 Section 6 ipReasmTimeout";
    }
    leaf reassembly-requireds {
      type uint64;
      description
        "The number of IPv4 fragments received which needed to be reassembled at this entity. Reference: RFC1213 Section 6 ipReasmReqds";
    }
    leaf reassembly-oks {
      type uint64;
      description
        "The number of IPv4 datagrams successfully re-assembled. Reference: RFC1213 Section 6 ipReasmOKs";
    }
    leaf reassembly-fails {
      type uint64;
      description
        "The number of failures detected by the IPv4 re-assembly algorithm (for whatever reason: timed out, errors, etc). Note that this is not necessarily a count of discarded IPv4 fragments since some algorithms can lose track of the number of fragments by combining them as they are received. Reference: RFC1213 Section 6 ipReasmFails";
    }
    leaf fragment-oks {
      type uint64;
      description
        "The number of IPv4 datagrams that have been successfully fragmented at this entity. Reference: RFC1213 Section 6 ipFragOKs";
    }
    leaf fragment-fails {
      type uint64;
      description
        "The number of IPv4 datagrams that have been discarded because they needed to be fragmented at this entity but could not be, e.g., because their 'Don't Fragment' flag was set. Reference: RFC1213 Section 6 ipFragFails";
    }
    leaf fragment-creates {
      type uint64;
      description
        "The number of IPv4 datagram fragments that have been generated as a result of fragmentation at this entity. Reference: RFC1213 Section 6 ipFragCreates";
    }
    description
      "Kernel IP Counters. Reference: Management Information Base for Network Management of TCP/IP-based internets: MIB-II (RFC1213)";
  }
  grouping ira-open-config-ip6-counters {
    leaf in-receives {
      type uint64;
      description
        "The total number of input IPv6 datagrams received from interfaces, including those received in error. Reference: RFC2465 Section 5 ipv6IfStatsInReceives";
    }
    leaf in-header-errors {
      type uint64;
      description
        "The number of input datagrams discarded due to errors in their IPv6 headers, including bad checksums, version number mismatch, other format errors, time-to-live exceeded, errors discovered in processing their IP options, etc. Reference: RFC2465 Section 5 ipv6IfStatsInDelivers";
    }
    leaf in-too-big-errors {
      type uint64;
      description
        "The number of input datagrams that could not be forwarded because their size exceeded the link MTU of outgoing interface. Reference: RFC2465 Section 5 ipv6IfStatsInTooBigErrors";
    }
    leaf in-no-routes {
      type uint64;
      description
        "The number of input datagrams discarded because no route could be found to transmit them to their destination. Reference: RFC2465 Section 5 ipv6IfStatsInNoRoutes";
    }
    leaf in-address-errors {
      type uint64;
      description
        "The number of input datagrams discarded because the IPv6 address in their IPv6 header's destination field was not a valid address to be received at this entity. This count includes invalid addresses (e.g., ::0) and unsupported addresses (e.g., addresses with unallocated prefixes). For entities which are not IPv6 routers and therefore do not forward datagrams, this counter includes datagrams discarded because the destination address was not a local address. Reference: RFC2465 Section 5 ipv6IfStatsInAddrErrors";
    }
    leaf in-unknown-protos {
      type uint64;
      description
        "The number of locally-addressed datagrams received successfully but discarded because of an unknown or unsupported protocol. This counter is incremented at the interface to which these datagrams were addressed which might not be necessarily the input interface for some of the datagrams. Reference: RFC2465 Section 5 ipv6IfStatsInUnknownProtos";
    }
    leaf in-truncated-pkts {
      type uint64;
      description
        "The number of input datagrams discarded because datagram frame didn't carry enough data. Reference: RFC2465 Section 5 ipv6IfStatsInTruncatedPkts";
    }
    leaf in-discards {
      type uint64;
      description
        "The number of input IPv6 datagrams for which no problems were encountered to prevent their continued processing, but which were discarded (e.g., for lack of buffer space). Note that this counter does not include any datagrams discarded while awaiting re-assembly. Reference: RFC2465 Section 5 ipv6IfStatsInDiscards";
    }
    leaf in-delivers {
      type uint64;
      description
        "The total number of datagrams successfully delivered to IPv6 user-protocols (including ICMP). Reference: RFC2465 Section 5 ipv6IfStatsInDelivers";
    }
    leaf out-forwarded-datagrams {
      type uint64;
      description
        "The number of output datagrams which this entity received and forwarded to their final destinations. In entities which do not act as IPv6 routers, this counter will include only those packets which were Source-Routed via this entity, and the Source-Route processing was successful. Reference: RFC2465 Section 5 ipv6IfStatsOutForwDatagrams";
    }
    leaf out-requests {
      type uint64;
      description
        "The total number of IPv6 datagrams which local IPv6 user-protocols (including ICMP) supplied to IPv6 in requests for transmission. Note that this counter does not include any datagrams counted in out-forwarded-datagrams. Reference: RFC2465 Section 5 ipv6IfStatsOutRequests";
    }
    leaf out-discards {
      type uint64;
      description
        "The number of output IPv6 datagrams for which no problem was encountered to prevent their transmission to their destination, but which were discarded (e.g., for lack of buffer space). Note that this counter would include datagrams counted in out-forwarded-datagrams if any such packets met this (discretionary) discard criterion. Reference: RFC2465 Section 5 ipv6IfStatsOutDiscards";
    }
    leaf out-no-routes {
      type uint64;
      description
        "The number of IPv6 datagrams discarded because no route could be found to transmit them to their destination. Notethat this counter includes any packets counted in out-forwarded-datagrams which meet this 'no-route' criterion. Note that this includes any datagrams which a host cannot route because all of its default routers are down.";
    }
    leaf reassembly-timeout {
      type uint64;
      description
        "The maximum number of seconds which received fragments are held while they are awaiting reassembly at this entity.";
    }
    leaf reassembly-requireds {
      type uint64;
      description
        "The number of IPv6 fragments received which needed to be reassembled. Reference: RFC2465 Section 5 ipv6IfStatsReasmReqds";
    }
    leaf reassembly-oks {
      type uint64;
      description
        "The number of IPv6 datagrams successfully reassembled. Reference: RFC2465 Section 5 ipv6IfStatsReasmOKs";
    }
    leaf reassembly-fails {
      type uint64;
      description
        "The number of failures detected by the IPv6 reassembly algorithm (for whatever reason: timed out, errors, etc.). Reference: RFC2465 Section 5 ipv6IfStatsReasmFails";
    }
    leaf fragment-oks {
      type uint64;
      description
        "The number of IPv6 datagrams that have been successfully fragmented. Reference: RFC2465 Section 5 ipv6IfStatsOutFragOKs";
    }
    leaf fragment-fails {
      type uint64;
      description
        "The number of IPv6 datagrams that have been discarded because they needed to be fragmented but could not be. Reference: RFC2465 Section 5 ipv6IfStatsOutFragFails";
    }
    leaf fragment-creates {
      type uint64;
      description
        "The number of output datagram fragments that have been generated as a result of fragmentation. Reference: RFC2465 Section 5 ipv6IfStatsOutFragCreates";
    }
    leaf in-multicast-pkts {
      type uint64;
      description
        "The number of multicast packets received. Reference: RFC2465 Section 5 ipv6IfStatsInMcastPkts";
    }
    leaf out-multicast-pkts {
      type uint64;
      description
        "The number of multicast packets transmitted. Reference: RFC2465 Section 5 ipv6IfStatsOutMcastPkts";
    }
    leaf in-octets {
      type uint64;
      description
        "The total number of input IPv6 octets received.";
    }
    leaf out-octets {
      type uint64;
      description
        "The total number of IPv6 octets transmitted.";
    }
    leaf in-mcast-octets {
      type uint64;
      description
        "The number of multicast octets received.";
    }
    leaf out-mcast-octets {
      type uint64;
      description
        "The number of multicast packets transmitted.";
    }
    leaf in-broadcast-octets {
      type uint64;
      description
        "The total number of broadcast octets received.";
    }
    leaf out-broadcast-octets {
      type uint64;
      description
        "The total number of broadcast octets transmitted.";
    }
    leaf in-no-ectpkts {
      type uint64;
      description
        "The number of IPv6 packets without any ECN (Explicit Congestion Notification) bits. Reference: RFC3168 Not-ECT";
    }
    leaf in-ect1-pkts {
      type uint64;
      description
        "The number of IPv6 packets with ECN (Explicit Congestion Notification) bits set. This counter is incremented when the ECT bit is not set and CE bit is set. Reference: RFC3168 ECT(1)";
    }
    leaf in-ect0-pkts {
      type uint64;
      description
        "The number of IPv6 packets with ECN (Explicit Congestion Notification) bits set. This counter is incremented when the ECT bit is set and CE bit is not set. Reference: RFC3168 ECT(0)";
    }
    leaf in-cepkts {
      type uint64;
      description
        "The number of IPv6 packets with both ECT and CE bit of ECN (Explicit Congestion Notification) set. This signifies congestion in the network. Reference: RFC3168 CE";
    }
    description
      "Kernel IPv6 Counters. Reference: Management Information Base for IP Version 6 (RFC2465)";
  }
  grouping ira-open-config-icmp-counters {
    leaf in-msgs {
      type uint64;
      description
        "The total number of ICMPv4 messages which theentity received. Note that this counter includesall those counted by icmp-in-errors. Reference: RFC1213 Section 6 icmpInMsgs";
    }
    leaf in-errors {
      type uint64;
      description
        "The number of ICMPv4 messages which the entity received but determined as having ICMPv4-specific errors (bad ICMPv4 checksums, bad length, etc.). Reference: RFC1213 Section 6 icmpInErrors";
    }
    leaf in-dest-unreachables {
      type uint64;
      description
        "The number of ICMPv4 Destination Unreachable messages received. Reference: RFC1213 Section 6 icmpInDestUnreachs";
    }
    leaf in-time-exceeds {
      type uint64;
      description
        "The number of ICMPv4 Time Exceeded messages received. Reference: RFC1213 Section 6 icmpInTimeExcds";
    }
    leaf in-param-problems {
      type uint64;
      description
        "The number of ICMPv4 Parameter Problem messages received. Reference: RFC1213 Section 6 icmpInParmProbs";
    }
    leaf in-src-quenches {
      type uint64;
      description
        "The number of ICMPv4 Source Quench messages received. Reference: RFC1213 Section 6 icmpInSrcQuenchs";
    }
    leaf in-redirects {
      type uint64;
      description
        "The number of ICMPv4 Redirect messages received. Reference: RFC1213 Section 6 icmpInRedirects";
    }
    leaf in-echo-requests {
      type uint64;
      description
        "The number of ICMPv4 Echo (request) messages received. Reference: RFC1213 Section 6 icmpInEchos";
    }
    leaf in-echo-replies {
      type uint64;
      description
        "The number of ICMPv4 Echo Reply messages received. Reference: RFC1213 Section 6 icmpInEchoReps";
    }
    leaf in-timestamp-requests {
      type uint64;
      description
        "The number of ICMPv4 Timestamp (request) messages received. Reference: RFC1213 Section 6 icmpInTimestamps";
    }
    leaf in-timestamp-replies {
      type uint64;
      description
        "The number of ICMPv4 Timestamp Reply messages received. Reference: RFC1213 Section 6 icmpInTimestampReps";
    }
    leaf in-addr-mask-requests {
      type uint64;
      description
        "The number of ICMPv4 Address Mask (request) messages received. Reference: RFC1213 Section 6 icmpInAddrMasks";
    }
    leaf in-addr-mask-replies {
      type uint64;
      description
        "The number of ICMPv4 Address Mask Reply messages received. Reference: RFC1213 Section 6 icmpInAddrMaskReps";
    }
    leaf in-checksum-errors {
      type uint64;
      description
        "Input Checksum Errors";
    }
    leaf out-msgs {
      type uint64;
      description
        "The total number of ICMPv4 messages which this entity attempted to send. Note that this counter includes all those counted by out-errors. Reference: RFC1213 Section 6 icmpOutMsgs";
    }
    leaf out-errors {
      type uint64;
      description
        "The number of ICMPv4 messages which this entity did not send due to problems discovered within ICMPv4 such as a lack of buffers. This value should not include errors discovered outside the ICMPv4 layer such as the inability of IP to route the resultant datagram. In some implementations there may be no types of error which contribute to this counter's value. Reference: RFC1213 Section 6 icmpOutErrors";
    }
    leaf out-dest-unreachables {
      type uint64;
      description
        "The number of ICMPv4 Destination Unreachable messages sent. Reference: RFC1213 Section 6 icmpOutDestUnreachs";
    }
    leaf out-time-exceeds {
      type uint64;
      description
        "The number of ICMPv4 Time Exceeded messages sent. Reference: RFC1213 Section 6 icmpOutTimeExds";
    }
    leaf out-param-problems {
      type uint64;
      description
        "The number of ICMPv4 Parameter Problem messages sent. Reference: RFC1213 Section 6 icmpOutParmProblems";
    }
    leaf out-src-quenches {
      type uint64;
      description
        "The number of ICMPv4 Source Quench messages sent. Reference: RFC1213 Section 6 icmpOutSrcQuenchs";
    }
    leaf out-redirects {
      type uint64;
      description
        "The number of ICMPv4 Redirect messages sent. For a host, this object will always be zero, since hosts do not send redirects. Reference: RFC1213 Section 6 icmpOutRedirects";
    }
    leaf out-echo-requests {
      type uint64;
      description
        "The number of ICMPv4 Echo (request) messages sent. Reference: RFC1213 Section 6 icmpOutEchos";
    }
    leaf out-echo-replies {
      type uint64;
      description
        "The number of ICMPv4 Echo Reply messages sent. Reference: RFC1213 Section 6 icmpOutEchoReps";
    }
    leaf out-timestamp-requests {
      type uint64;
      description
        "The number of ICMPv4 Timestamp (request) messages sent. Reference: RFC1213 Section 6 icmpOutTimestamps";
    }
    leaf out-timestamp-replies {
      type uint64;
      description
        "The number of ICMPv4 Timestamp Reply messages sent. Reference: RFC1213 Section 6 icmpOutTimestampReps";
    }
    leaf out-addr-mask-requests {
      type uint64;
      description
        "The number of ICMPv4 Address Mask Request messages sent. Reference: RFC1213 Section 6 icmpOutAddrMasks";
    }
    leaf out-addr-mask-replies {
      type uint64;
      description
        "The number of ICMPv4 Address Mask Reply messages sent. Reference: RFC1213 Section 6 icmpOutAddrMaskReps";
    }
    description
      "Kernel ICMP Counters. Reference: Management Information Base for Network Management of TCP/IP-based internets: MIB-II (RFC1213)";
  }
  grouping ira-open-config-icmp6-counters {
    leaf in-msgs {
      type uint64;
      description
        "The total number of ICMPv6 messages which the entity received. Note that this counter includes all those counted by in-errors. Reference: RFC2466 Section 3 ipv6IfIcmpInMsgs";
    }
    leaf in-errors {
      type uint64;
      description
        "The number of ICMPv6 messages which the entity received but determined as having ICMPv6-specific errors (bad ICMPv6 checksums, bad length, etc.). Reference: RFC2466 Section 3 ipv6IfIcmpInErrors";
    }
    leaf in-dest-unreachables {
      type uint64;
      description
        "The number of ICMPv6 Destination Unreachable messages received. Reference: RFC2466 Section 3 ipv6IfIcmpInDestUnreachs";
    }
    leaf in-time-exceeds {
      type uint64;
      description
        "The number of ICMPv6 Time Exceeded messages received. Reference: RFC2466 Section 3 ipv6IfIcmpInTimeExcds";
    }
    leaf in-param-problems {
      type uint64;
      description
        "The number of ICMPv6 Parameter Problem messages received. Reference: RFC2466 Section 3 ipv6IfIcmpInParmProblems";
    }
    leaf in-redirects {
      type uint64;
      description
        "The number of ICMPv6 Redirect messages received. Reference: RFC2466 Section 3 ipv6IfIcmpInRedirects";
    }
    leaf in-echo-requests {
      type uint64;
      description
        "The number of ICMPv6 Echo request messages received. Reference: RFC2466 Section 3 ipv6IfIcmpInEchos";
    }
    leaf in-echo-replies {
      type uint64;
      description
        "The number of ICMPv6 Echo Reply messages received. Reference: RFC2466 Section 3 ipv6IfIcmpInEchoReplies";
    }
    leaf in-group-membership-queries {
      type uint64;
      description
        "The number of ICMPv6 Group Membership Query messages received. Reference: RFC2466 Section 3 ipv6IfIcmpInGroupMembQueries";
    }
    leaf in-group-membership-responses {
      type uint64;
      description
        "The number of ICMPv6 Group Membership Response messages received. Reference: RFC2466 Section 3 ipv6IfIcmpInGroupMembResponses";
    }
    leaf in-group-membership-reductions {
      type uint64;
      description
        "The number of ICMPv6 Group Membership Reduction messages received. Reference: RFC2466 Section 3 ipv6IfIcmpInGroupMembReductions";
    }
    leaf in-router-advertisements {
      type uint64;
      description
        "The number of ICMPv6 Router Advertisement messages received. Reference: RFC2466 Section 3 ipv6IfIcmpInRouterAdvertisements";
    }
    leaf in-router-solicits {
      type uint64;
      description
        "The number of ICMPv6 Router Solicit messages received. Reference: RFC2466 Section 3 ipv6IfIcmpInRouterSolicits";
    }
    leaf in-neighbor-solicits {
      type uint64;
      description
        "The number of ICMPv6 Neighbor Solicit messages received. Reference: RFC2466 Section 3 ipv6IfIcmpInNeighborSolicits";
    }
    leaf in-neighbor-advertisements {
      type uint64;
      description
        "The number of ICMPv6 Neighbor Advertisement messages received. Reference: RFC2466 Section 3 ipv6IfIcmpInNeighborAdvertisements";
    }
    leaf in-pkt-too-bigs {
      type uint64;
      description
        "The number of ICMPv6 packets received with Packet Too Big message. Reference: RFC2466 Section 3 ipv6IfIcmpInPktTooBigs";
    }
    leaf in-mldv2-reports {
      type uint64;
      description
        "The number of Multicast Listener Discovery version 2 (MLDv2) report messages received.";
    }
    leaf out-msgs {
      type uint64;
      description
        "The total number of ICMPv6 messages which this entity attempted to send.  Note that this counter includes all those counted by icmp-out-errors. Reference: RFC2466 Section 3 ipv6IfIcmpOutMsgs";
    }
    leaf out-errors {
      type uint64;
      description
        "The number of ICMPv6 messages which this entity did not send due to problems discovered within ICMPv6 such as a lack of buffers. This value should not include errors discovered outside the ICMPv6 layer such as the inability of IP to route the resultant datagram. In some implementations there may be no types of error which contribute to this counter's value. Reference: RFC2466 Section 3 ipv6IfIcmpOutErrors";
    }
    leaf out-dest-unreachables {
      type uint64;
      description
        "The number of ICMPv6 Destination Unreachable messages sent. Reference: RFC2466 Section 3 ipv6IfIcmpOutDestUnreachs";
    }
    leaf out-time-exceeds {
      type uint64;
      description
        "The number of ICMPv6 Time Exceeded messages sent. Reference: RFC2466 Section 3 ipv6IfIcmpOutTimeExcds";
    }
    leaf out-param-problems {
      type uint64;
      description
        "The number of ICMPv6 Parameter Problem messages sent. Reference: RFC2466 Section 3 ipv6IfIcmpOutParmProblems";
    }
    leaf out-redirects {
      type uint64;
      description
        "The number of ICMPv6 Redirect messages sent. For a host, this object will always be zero, since hosts do not send redirects. Reference: RFC2466 Section 3 ipv6IfIcmpOutRedirects";
    }
    leaf out-echo-requests {
      type uint64;
      description
        "The number of ICMPv6 Echo request messages sent. Reference: RFC2466 Section 3 ipv6IfIcmpOutEchos";
    }
    leaf out-echo-replies {
      type uint64;
      description
        "The number of ICMPv6 Echo Reply messages sent. Reference: RFC2466 Section 3 ipv6IfIcmpOutEchoReplies";
    }
    leaf out-group-membership-queries {
      type uint64;
      description
        "The number of ICMPv6 Group Membership Query messages sent. Reference: RFC2466 Section 3 ipv6IfIcmpOutGroupMembQueries";
    }
    leaf out-group-membership-responses {
      type uint64;
      description
        "The number of ICMPv6 Group Membership Response messages sent. Reference: RFC2466 Section 3 ipv6IfIcmpOutGroupMembResponses";
    }
    leaf out-group-membership-reductions {
      type uint64;
      description
        "The number of ICMPv6 Group Membership Reduction messages sent. Reference: RFC2466 Section 3 ipv6IfIcmpOutGroupMembReductions";
    }
    leaf out-router-advertisements {
      type uint64;
      description
        "The number of ICMPv6 Router Advertisement messages sent. Reference: RFC2466 Section 3 ipv6IfIcmpOutRouterAdvertisements";
    }
    leaf out-router-solicits {
      type uint64;
      description
        "The number of ICMPv6 Router Solicit messages sent. Reference: RFC2466 Section 3 ipv6IfIcmpOutRouterSolicits";
    }
    leaf out-neighbor-solicits {
      type uint64;
      description
        "The number of ICMPv6 Neighbor Solicit messages sent. Reference: RFC2466 Section 3 ipv6IfIcmpOutNeighborSolicits";
    }
    leaf out-neighbor-advertisements {
      type uint64;
      description
        "The number of ICMPv6 Router Advertisement messages sent. Reference: RFC2466 Section 3 ipv6IfIcmpOutNeighborAdvertisements";
    }
    leaf out-pkt-too-bigs {
      type uint64;
      description
        "The number of ICMPv6 packets sent with Packet Too Big message. Reference: RFC2466 Section 3 ipv6IfIcmpOutPktTooBigs";
    }
    leaf out-mldv2-reports {
      type uint64;
      description
        "The number of Multicast Listener Discovery version 2 (MLDv2) report messages sent.";
    }
    description
      "Kernel ICMP6 Counters. Reference: Management Information Base for IP Version 6: ICMPv6 Group (RFC2466)";
  }
  grouping ira-open-config-tcp-counters {
    leaf rto-algorithm {
      type uint64;
      description
        "The algorithm used to determine the timeout value used for retransmitting unacknowledged octets. Reference: RFC1213 Section 6 tcpRtoAlgorithm";
    }
    leaf rto-min {
      type uint64;
      description
        "The minimum value permitted by a TCP implementation for the retransmission timeout, measured in milliseconds. More refined semantics for objects of this type depend upon the algorithm used to determine the retransmission timeout. Reference: RFC1213 Section 6 tcpRtoMin";
    }
    leaf rto-max {
      type uint64;
      description
        "The maximum value permitted by a TCP implementation for the retransmission timeout, measured in milliseconds. More refined semantics for objects of this type depend upon the algorithm used to determine the retransmission timeout. Reference: RFC1213 Section 6 tcpRtoMax";
    }
    leaf max-connections {
      type int64;
      description
        "The limit on the total number of TCP connections the entity can support. In entities where the maximum number of connections is dynamic, this object should contain the value -1. Reference: RFC1213 Section 6 tcpMaxConn";
    }
    leaf active-opens {
      type uint64;
      description
        "The number of times TCP connections have made a direct transition to the SYN-SENT state from the CLOSED state. Reference: RFC1213 Section 6 tcpActiveOpens";
    }
    leaf passive-opens {
      type uint64;
      description
        "The number of times TCP connections have made a direct transition to the SYN-RCVD state from the LISTEN state. Reference: RFC1213 Section 6 tcpPassiveOpens";
    }
    leaf attempt-fails {
      type uint64;
      description
        "The number of times TCP connections have made a direct transition to the CLOSED state from either the SYN-SENT state or the SYN-RCVD state, plus the number of times TCP connections have made a direct transition to the LISTEN state from the SYN-RCVD state. Reference: RFC1213 Section 6 tcpAttemptFails";
    }
    leaf established-resets {
      type uint64;
      description
        "The number of times TCP connections have made a direct transition to the CLOSED state from either the ESTABLISHED state or the CLOSE-WAIT state. Reference: RFC1213 Section 6 tcpEstabResets";
    }
    leaf current-established {
      type uint64;
      description
        "The number of TCP connections for which the current state is either ESTABLISHED or CLOSE-WAIT. Reference: RFC1213 Section 6 tcpCurrEstab";
    }
    leaf in-segments {
      type uint64;
      description
        "The total number of segments received, including those received in error. This count includes segments received on currently established connections. Reference: RFC1213 Section 6 tcpInSegs";
    }
    leaf out-segments {
      type uint64;
      description
        "The total number of segments sent, including those on current connections but excluding those containing only retransmitted octets. Reference: RFC1213 Section 6 tcpOutSegs";
    }
    leaf retransmitted-segments {
      type uint64;
      description
        "The total number of segments retransmitted-that is, the number of TCP segments transmitted containing one or more previously transmitted octets. Reference: RFC1213 Section 6 tcpRetransSegs";
    }
    leaf in-errors {
      type uint64;
      description
        "The total number of segments received in error (e.g., bad TCP checksums). Reference: RFC1213 Section 6 tcpInErrs";
    }
    leaf out-resets {
      type uint64;
      description
        "The number of TCP segments sent containing the RST flag. Reference: RFC1213 Section 6 tcpOutRsts";
    }
    leaf in-checksum-errors {
      type uint64;
      description
        "Checksum errors";
    }
    description
      "Kernel TCP Counters. Reference: Management Information Base for Network Management of TCP/IP-based internets: MIB-II (RFC1213)";
  }
  grouping ira-open-config-udp-counters {
    leaf in-datagrams {
      type uint64;
      description
        "The total number of UDP datagrams delivered to UDP users. Reference: RFC1213 Section 6 udpInDatagrams";
    }
    leaf no-ports {
      type uint64;
      description
        "The total number of received UDP datagrams for which there was no application at the destination port. Reference: RFC1213 Section 6 udpNoPorts";
    }
    leaf in-errors {
      type uint64;
      description
        "The number of received UDP datagrams that could not be delivered for reasons other than the lack of an application at the destination port. Reference: RFC1213 Section 6 udpInErrors";
    }
    leaf out-datagrams {
      type uint64;
      description
        "The total number of UDP datagrams sent from this entity. Reference: RFC1213 Section 6 udpOutDatagrams";
    }
    leaf receive-buffer-errors {
      type uint64;
      description
        "UDP datagrams Receive Buffer Errors.";
    }
    leaf send-buffer-errors {
      type uint64;
      description
        "UDP datagrams Send Buffer Errors.";
    }
    leaf in-checksum-errors {
      type uint64;
      description
        "UDP checksum errors";
    }
    leaf ignored-multi {
      type uint64;
      description
        "The number of multicast packets that were dropped and not processed by the system ";
    }
    description
      "Kernel UDP Counters. Reference: Management Information Base for Network Management of TCP/IP-based internets: MIB-II (RFC1213)";
  }
  augment "/openconfig-network-instance:network-instances/openconfig-network-instance:network-instance" {
    container kernel {
      container ip {
        container state {
          container counters {
            uses ira-open-config-ip-counters;
            config false;
            description
              "counters container";
          }
          description
            "state container";
        }
        description
          "ip container";
      }
      container ip6 {
        container state {
          container counters {
            uses ira-open-config-ip6-counters;
            config false;
            description
              "counters container";
          }
          description
            "state container";
        }
        description
          "ip6 container";
      }
      container icmp {
        container state {
          container counters {
            uses ira-open-config-icmp-counters;
            config false;
            description
              "counters container";
          }
          description
            "state container";
        }
        description
          "icmp container";
      }
      container icmp6 {
        container state {
          container counters {
            uses ira-open-config-icmp6-counters;
            config false;
            description
              "counters container";
          }
          description
            "state container";
        }
        description
          "icmp6 container";
      }
      container udp {
        container state {
          container counters {
            uses ira-open-config-udp-counters;
            config false;
            description
              "counters container";
          }
          description
            "state container";
        }
        description
          "udp container";
      }
      container udp6 {
        container state {
          container counters {
            uses ira-open-config-udp-counters;
            config false;
            description
              "counters container";
          }
          description
            "state container";
        }
        description
          "udp6 container";
      }
      container tcp {
        container state {
          container counters {
            uses ira-open-config-tcp-counters;
            config false;
            description
              "counters container";
          }
          description
            "state container";
        }
        description
          "tcp container";
      }
      description
        "kernel container";
    }
  }
} // main-yang
