module arista-open-config-lib-open-config-system-session-config {
  yang-version 1;
  namespace "http://arista.com/yang/arista-open-config-lib-open-config-system-session-config";
  prefix "arista-open-config-lib-open-config-system-session-config";
  
  import openconfig-extensions { prefix "oc-ext"; }
  
  organization
    "Arista Networks <http://arista.com/>";
  contact
    "Arista Networks <http://arista.com/>";
  
  description
    "Defines config diff config
    THIS YANG MODULE WAS GENERATED. DO NOT EDIT THIS FILE.";
  
  oc-ext:openconfig-version "0.1.0";
  
  revision "2024-02-05" {
    description
      "Version 0.1.0, generated on 2024-02-05";
    reference "0.1.0";
  }
  // covered-by: arista-system-session.yang
  
  typedef open-config-system-session-max-history-size {
    type uint8;
    default 20;
    description
      "open-config-system-session-max-history-size";
  }
  typedef open-config-system-session-enable-config-terminal {
    type boolean;
    default true;
    description
      "open-config-system-session-enable-config-terminal";
  }
  grouping open-config-system-session-config {
    leaf max-history-size {
      type open-config-system-session-max-history-size;
      description
        "";
    }
    leaf enable-config-terminal {
      type open-config-system-session-enable-config-terminal;
      description
        "";
    }
    leaf enable-diff {
      type boolean;
      description
        "";
    }
    description
      "";
  }
  container system {
    container session {
      container config {
        uses open-config-system-session-config;
        description
          "config container";
      }
      oc-ext:telemetry-atomic;
      description
        "session container";
    }
    oc-ext:telemetry-atomic;
    description
      "system container";
  }
} // main-yang
