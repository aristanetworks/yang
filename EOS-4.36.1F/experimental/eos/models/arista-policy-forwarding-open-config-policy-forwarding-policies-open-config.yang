module arista-policy-forwarding-open-config-policy-forwarding-policies-open-config {
  yang-version 1;
  namespace "http://arista.com/yang/arista-policy-forwarding-open-config-policy-forwarding-policies-open-config";
  prefix "arista-policy-forwarding-open-config-policy-forwarding-policies-open-config";
  
  import openconfig-extensions { prefix "oc-ext"; }
  import arista-acl-acl-open-config-packet-match-types { prefix "arista-acl-acl-open-config-packet-match-types"; }
  import openconfig-acl { prefix "openconfig-acl"; }
  import openconfig-icmpv4-types { prefix "openconfig-icmpv4-types"; }
  import openconfig-icmpv6-types { prefix "openconfig-icmpv6-types"; }
  import openconfig-inet-types { prefix "openconfig-inet-types"; }
  import openconfig-packet-match-types { prefix "openconfig-packet-match-types"; }
  import openconfig-yang-types { prefix "openconfig-yang-types"; }
  
  organization
    "Arista Networks <http://arista.com/>";
  contact
    "Arista Networks <http://arista.com/>";
  
  description
    "This is the model for policy forwarding model
    THIS YANG MODULE WAS GENERATED. DO NOT EDIT THIS FILE.";
  
  oc-ext:openconfig-version "1.0.0";
  
  revision "2025-04-22" {
    description
      "Version 1.0.0, generated on 2025-04-22";
    reference "1.0.0";
  }
  // covered-by: openconfig-network-instance.yang,arista-policy-forwarding-open-config-policy-forwarding-policies-open-config-augment.yang
  
  typedef policy-forwarding-open-config-pf-policy-type {
    type enumeration {
      enum PBR_POLICY {
        value 0;
        description
          "PBR_POLICY";
      }
      enum VRF_SELECTION_POLICY {
        value 1;
        description
          "VRF_SELECTION_POLICY";
      }
      enum MATCH_ACTION_POLICY {
        value 2;
        description
          "MATCH_ACTION_POLICY";
      }
    }
    description
      "policy-forwarding-open-config-pf-policy-type";
  }
  grouping policy-forwarding-open-config-pf-policy-key {
    leaf policy-id {
      type string;
      description
        "policy-id";
    }
    description
      "policy-forwarding-open-config-pf-policy-key";
  }
  grouping policy-forwarding-open-config-pf-policy-config {
    leaf policy-id {
      type string;
      description
        "policy-id";
    }
    leaf type {
      type policy-forwarding-open-config-pf-policy-type;
      description
        "type";
    }
    description
      "policy-forwarding-open-config-pf-policy-config";
  }
  grouping policy-forwarding-open-config-pf-policy-rule-config {
    leaf sequence-id {
      type uint32;
      description
        "sequence-id";
    }
    description
      "policy-forwarding-open-config-pf-policy-rule-config";
  }
  grouping policy-forwarding-open-config-pf-policy-rule-ip-common-config {
    leaf source-address-prefix-set {
      type string;
      description
        "source-address-prefix-set";
    }
    leaf destination-address-prefix-set {
      type string;
      description
        "destination-address-prefix-set";
    }
    leaf dscp {
      type uint8;
      description
        "dscp";
    }
    leaf-list dscp-set {
      type uint8;
      oc-ext:telemetry-atomic;
      description
        "dscp-set";
    }
    leaf length {
      type uint16;
      description
        "length";
    }
    leaf protocol {
      type openconfig-packet-match-types:ip-protocol-type;
      description
        "protocol";
    }
    leaf hop-limit {
      type uint8;
      description
        "hop-limit";
    }
    description
      "policy-forwarding-open-config-pf-policy-rule-ip-common-config";
  }
  grouping policy-forwarding-open-config-pf-policy-rule-icmpv4-config {
    leaf type {
      type identityref {
        base "openconfig-icmpv4-types:TYPE";
      }
      description
        "type";
    }
    leaf code {
      type identityref {
        base "openconfig-icmpv4-types:CODE";
      }
      description
        "code";
    }
    description
      "policy-forwarding-open-config-pf-policy-rule-icmpv4-config";
  }
  grouping policy-forwarding-open-config-pf-policy-rule-icmpv4 {
    container config {
      uses policy-forwarding-open-config-pf-policy-rule-icmpv4-config;
      description
        "config";
    }
    container state {
      uses policy-forwarding-open-config-pf-policy-rule-icmpv4-config;
      config false;
      description
        "state";
    }
    description
      "policy-forwarding-open-config-pf-policy-rule-icmpv4";
  }
  grouping policy-forwarding-open-config-pf-policy-rule-icmpv6-config {
    leaf type {
      type identityref {
        base "openconfig-icmpv6-types:TYPE";
      }
      description
        "type";
    }
    leaf code {
      type identityref {
        base "openconfig-icmpv6-types:CODE";
      }
      description
        "code";
    }
    description
      "policy-forwarding-open-config-pf-policy-rule-icmpv6-config";
  }
  grouping policy-forwarding-open-config-pf-policy-rule-icmpv6 {
    container config {
      uses policy-forwarding-open-config-pf-policy-rule-icmpv6-config;
      description
        "config";
    }
    container state {
      uses policy-forwarding-open-config-pf-policy-rule-icmpv6-config;
      config false;
      description
        "state";
    }
    description
      "policy-forwarding-open-config-pf-policy-rule-icmpv6";
  }
  grouping policy-forwarding-open-config-pf-policy-rule-ipv4-config {
    leaf source-address {
      type openconfig-inet-types:ipv4-prefix;
      description
        "source-address";
    }
    leaf destination-address {
      type openconfig-inet-types:ipv4-prefix;
      description
        "destination-address";
    }
    leaf-list fragment-offsets {
      type openconfig-packet-match-types:fragment-offset-range;
      oc-ext:telemetry-atomic;
      description
        "fragment-offsets";
    }
    uses policy-forwarding-open-config-pf-policy-rule-ip-common-config;
    description
      "policy-forwarding-open-config-pf-policy-rule-ipv4-config";
  }
  grouping policy-forwarding-open-config-pf-policy-rule-ipv6-config {
    leaf source-address {
      type openconfig-inet-types:ipv6-prefix;
      description
        "source-address";
    }
    leaf destination-address {
      type openconfig-inet-types:ipv6-prefix;
      description
        "destination-address";
    }
    uses policy-forwarding-open-config-pf-policy-rule-ip-common-config;
    description
      "policy-forwarding-open-config-pf-policy-rule-ipv6-config";
  }
  grouping policy-forwarding-open-config-pf-policy-rule-ipv4 {
    container config {
      uses policy-forwarding-open-config-pf-policy-rule-ipv4-config;
      description
        "config";
    }
    container state {
      uses policy-forwarding-open-config-pf-policy-rule-ipv4-config;
      config false;
      description
        "state";
    }
    container icmpv4 {
      uses policy-forwarding-open-config-pf-policy-rule-icmpv4;
      description
        "icmpv4";
    }
    description
      "policy-forwarding-open-config-pf-policy-rule-ipv4";
  }
  grouping policy-forwarding-open-config-pf-policy-rule-ipv6 {
    container config {
      uses policy-forwarding-open-config-pf-policy-rule-ipv6-config;
      description
        "config";
    }
    container state {
      uses policy-forwarding-open-config-pf-policy-rule-ipv6-config;
      config false;
      description
        "state";
    }
    container icmpv6 {
      uses policy-forwarding-open-config-pf-policy-rule-icmpv6;
      description
        "icmpv6";
    }
    description
      "policy-forwarding-open-config-pf-policy-rule-ipv6";
  }
  grouping policy-forwarding-open-config-pf-policy-rule-transport-config {
    leaf source-port {
      type openconfig-packet-match-types:port-num-range;
      description
        "source-port";
    }
    leaf destination-port {
      type openconfig-packet-match-types:port-num-range;
      description
        "destination-port";
    }
    leaf source-port-set {
      type string;
      description
        "source-port-set";
    }
    leaf destination-port-set {
      type string;
      description
        "destination-port-set";
    }
    leaf detail-mode {
      type arista-acl-acl-open-config-packet-match-types:acl-open-config-detail-mode;
      description
        "detail-mode";
    }
    leaf explicit-detail-match-mode {
      type arista-acl-acl-open-config-packet-match-types:acl-open-config-explicit-detail-mode;
      description
        "explicit-detail-match-mode";
    }
    leaf-list explicit-tcp-flags {
      type identityref {
        base "openconfig-packet-match-types:TCP_FLAGS";
      }
      oc-ext:telemetry-atomic;
      description
        "explicit-tcp-flags";
    }
    leaf builtin-detail {
      type arista-acl-acl-open-config-packet-match-types:acl-open-config-builtin-detail;
      description
        "builtin-detail";
    }
    description
      "policy-forwarding-open-config-pf-policy-rule-transport-config";
  }
  grouping policy-forwarding-open-config-pf-policy-rule-transport {
    container config {
      uses policy-forwarding-open-config-pf-policy-rule-transport-config;
      description
        "config";
    }
    container state {
      uses policy-forwarding-open-config-pf-policy-rule-transport-config;
      config false;
      description
        "state";
    }
    description
      "policy-forwarding-open-config-pf-policy-rule-transport";
  }
  grouping policy-forwarding-open-config-pf-policy-rule-l2-config {
    leaf source-mac {
      type openconfig-yang-types:mac-address;
      description
        "source-mac";
    }
    leaf destination-mac {
      type openconfig-yang-types:mac-address;
      description
        "destination-mac";
    }
    leaf ethertype {
      type openconfig-packet-match-types:ethertype-type;
      description
        "ethertype";
    }
    description
      "policy-forwarding-open-config-pf-policy-rule-l2-config";
  }
  grouping policy-forwarding-open-config-pf-policy-rule-l2 {
    container config {
      uses policy-forwarding-open-config-pf-policy-rule-l2-config;
      description
        "config";
    }
    container state {
      uses policy-forwarding-open-config-pf-policy-rule-l2-config;
      config false;
      description
        "state";
    }
    description
      "policy-forwarding-open-config-pf-policy-rule-l2";
  }
  grouping policy-forwarding-open-config-pf-policy-rule-action-config {
    leaf discard {
      type boolean;
      description
        "discard";
    }
    leaf decapsulate-gre {
      type boolean;
      description
        "decapsulate-gre";
    }
    leaf decapsulate-mpls-in-udp {
      type boolean;
      description
        "decapsulate-mpls-in-udp";
    }
    leaf decapsulate-gue {
      type boolean;
      description
        "decapsulate-gue";
    }
    leaf network-instance {
      type string;
      description
        "network-instance";
    }
    leaf decap-network-instance {
      type string;
      description
        "decap-network-instance";
    }
    leaf decap-fallback-network-instance {
      type string;
      description
        "decap-fallback-network-instance";
    }
    leaf post-decap-network-instance {
      type string;
      description
        "post-decap-network-instance";
    }
    description
      "policy-forwarding-open-config-pf-policy-rule-action-config";
  }
  grouping policy-forwarding-open-config-pf-policy-rule-action {
    container config {
      uses policy-forwarding-open-config-pf-policy-rule-action-config;
      description
        "config";
    }
    container state {
      uses policy-forwarding-open-config-pf-policy-rule-action-config;
      config false;
      description
        "state";
    }
    description
      "policy-forwarding-open-config-pf-policy-rule-action";
  }
  grouping policy-forwarding-open-config-pf-policy-rule {
    leaf sequence-id {
      type uint32;
      description
        "sequence-id";
    }
    container config {
      uses policy-forwarding-open-config-pf-policy-rule-config;
      description
        "config";
    }
    container l2 {
      uses policy-forwarding-open-config-pf-policy-rule-l2;
      description
        "l2";
    }
    container ipv4 {
      uses policy-forwarding-open-config-pf-policy-rule-ipv4;
      description
        "ipv4";
    }
    container ipv6 {
      uses policy-forwarding-open-config-pf-policy-rule-ipv6;
      description
        "ipv6";
    }
    container transport {
      uses policy-forwarding-open-config-pf-policy-rule-transport;
      description
        "transport";
    }
    container action {
      uses policy-forwarding-open-config-pf-policy-rule-action;
      description
        "action";
    }
    description
      "policy-forwarding-open-config-pf-policy-rule";
  }
  grouping policy-forwarding-open-config-pf-policy-rules {
    list rule {
      key "sequence-id";
      uses policy-forwarding-open-config-pf-policy-rule;
      description
        "rule";
    }
    description
      "policy-forwarding-open-config-pf-policy-rules";
  }
  grouping policy-forwarding-open-config-pf-policy {
    uses policy-forwarding-open-config-pf-policy-key;
    container config {
      uses policy-forwarding-open-config-pf-policy-config;
      description
        "config";
    }
    container state {
      uses policy-forwarding-open-config-pf-policy-config;
      config false;
      description
        "state";
    }
    container rules {
      uses policy-forwarding-open-config-pf-policy-rules;
      description
        "rules";
    }
    description
      "policy-forwarding-open-config-pf-policy";
  }
  grouping policy-forwarding-open-config-pf-policy-container {
    leaf name {
      type string;
      description
        "name of the grouping";
    }
    description
      "policy-forwarding-open-config-pf-policy-container";
  }
  grouping policy-forwarding-open-config-pf-global-config {
    leaf global-decap-policy {
      type string;
      description
        "global-decap-policy";
    }
    description
      "policy-forwarding-open-config-pf-global-config";
  }
  grouping policy-forwarding-open-config-pf-global {
    container config {
      uses policy-forwarding-open-config-pf-global-config;
      description
        "config";
    }
    container state {
      uses policy-forwarding-open-config-pf-global-config;
      config false;
      description
        "state";
    }
    description
      "policy-forwarding-open-config-pf-global";
  }
  grouping policy-forwarding-open-config-pf-global-container {
    leaf name {
      type string;
      description
        "name of the grouping";
    }
    description
      "policy-forwarding-open-config-pf-global-container";
  }
  container network-instances {
    list network-instance {
      key "name";
      oc-ext:telemetry-atomic;
      leaf name {
        type string;
        description
          "name leaf used as key for network-instance list";
      }
      container policy-forwarding {
        uses policy-forwarding-open-config-pf-global;
        container policies {
          list policy {
            key "policy-id";
            oc-ext:telemetry-atomic;
            uses policy-forwarding-open-config-pf-policy;
            description
              "policy list";
          }
          oc-ext:telemetry-atomic;
          description
            "policies container";
        }
        description
          "policy-forwarding container";
      }
      description
        "network-instance list";
    }
    oc-ext:telemetry-atomic;
    description
      "network-instances container";
  }
} // main-yang
