module arista-policy-forwarding-open-config-policy-forwarding-interfaces-open-config {
  yang-version 1;
  namespace "http://arista.com/yang/arista-policy-forwarding-open-config-policy-forwarding-interfaces-open-config";
  prefix "arista-policy-forwarding-open-config-policy-forwarding-interfaces-open-config";
  
  import openconfig-extensions { prefix "oc-ext"; }
  import openconfig-interfaces { prefix "openconfig-interfaces"; }
  
  organization
    "Arista Networks <http://arista.com/>";
  contact
    "Arista Networks <http://arista.com/>";
  
  description
    "This is the model for policy forwarding interface application
    THIS YANG MODULE WAS GENERATED. DO NOT EDIT THIS FILE.";
  
  oc-ext:openconfig-version "1.0.0";
  
  revision "2025-07-23" {
    description
      "Version 1.0.0, generated on 2025-07-23";
    reference "1.0.0";
  }
  // covered-by: openconfig-network-instance.yang
  
  grouping policy-forwarding-open-config-pf-interface-key {
    leaf interface-id {
      type openconfig-interfaces:interface-id;
      description
        "interface-id";
    }
    description
      "policy-forwarding-open-config-pf-interface-key";
  }
  grouping policy-forwarding-open-config-pf-interface-config {
    leaf interface-id {
      type openconfig-interfaces:interface-id;
      description
        "interface-id";
    }
    leaf apply-forwarding-policy {
      type string;
      description
        "apply-forwarding-policy";
    }
    leaf apply-vrf-selection-policy {
      type string;
      description
        "apply-vrf-selection-policy";
    }
    description
      "policy-forwarding-open-config-pf-interface-config";
  }
  grouping policy-forwarding-open-config-pf-interface-ref-config {
    leaf interface {
      type string;
      description
        "interface";
    }
    leaf subinterface {
      type uint32;
      description
        "subinterface";
    }
    description
      "policy-forwarding-open-config-pf-interface-ref-config";
  }
  grouping policy-forwarding-open-config-pf-interface-ref {
    container config {
      uses policy-forwarding-open-config-pf-interface-ref-config;
      description
        "config";
    }
    container state {
      uses policy-forwarding-open-config-pf-interface-ref-config;
      config false;
      description
        "state";
    }
    description
      "policy-forwarding-open-config-pf-interface-ref";
  }
  grouping policy-forwarding-open-config-pf-interface {
    uses policy-forwarding-open-config-pf-interface-key;
    container config {
      uses policy-forwarding-open-config-pf-interface-config;
      description
        "config";
    }
    container state {
      uses policy-forwarding-open-config-pf-interface-config;
      config false;
      description
        "state";
    }
    container interface-ref {
      uses policy-forwarding-open-config-pf-interface-ref;
      description
        "interface-ref";
    }
    description
      "policy-forwarding-open-config-pf-interface";
  }
  container network-instances {
    list network-instance {
      key "name";
      oc-ext:telemetry-atomic;
      leaf name {
        type string;
        description
          "name leaf used as key for network-instance list";
      }
      container policy-forwarding {
        container interfaces {
          list interface {
            key "interface-id";
            oc-ext:telemetry-atomic;
            uses policy-forwarding-open-config-pf-interface;
            description
              "interface list";
          }
          oc-ext:telemetry-atomic;
          description
            "interfaces container";
        }
        oc-ext:telemetry-atomic;
        description
          "policy-forwarding container";
      }
      description
        "network-instance list";
    }
    oc-ext:telemetry-atomic;
    description
      "network-instances container";
  }
} // main-yang
