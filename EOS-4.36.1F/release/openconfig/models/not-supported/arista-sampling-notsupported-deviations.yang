module arista-sampling-notsupported-deviations {
  namespace "http://arista.com/yang/openconfig/sampling/notsupported-deviations";
  prefix arista-sampling-notsupported-deviations;

  import openconfig-sampling {
    prefix oc-sampling;
  }
  import openconfig-sampling-sflow {
    prefix oc-sflow;
  }

  organization
    "Arista Networks, Inc.";
  contact
    "Arista Networks, Inc.
     Product Support";
  description
    "This module contains OpenConfig sampling deviations in Arista EOS.
     Copyright (c) 2020 Arista Networks, Inc. All rights reserved.";

  revision 2026-06-09 {
    description
      "Auto-generated not-supported deviations for unsupported paths";
  }

  deviation "/oc-sampling:sampling/oc-sflow:sflow/oc-sflow:collectors/oc-sflow:collector/oc-sflow:config/oc-sflow:max-datagram-size" {
    description
      "Not-supported deviation.";
    deviate not-supported;
  }

  deviation "/oc-sampling:sampling/oc-sflow:sflow/oc-sflow:collectors/oc-sflow:collector/oc-sflow:state/oc-sflow:max-datagram-size" {
    description
      "Not-supported deviation.";
    deviate not-supported;
  }

  deviation "/oc-sampling:sampling/oc-sflow:sflow/oc-sflow:collectors/oc-sflow:collector/oc-sflow:state/oc-sflow:packets-sent" {
    description
      "Not-supported deviation.";
    deviate not-supported;
  }

  deviation "/oc-sampling:sampling/oc-sflow:sflow/oc-sflow:config/oc-sflow:agent-id-ipv4" {
    description
      "Not-supported deviation.";
    deviate not-supported;
  }

  deviation "/oc-sampling:sampling/oc-sflow:sflow/oc-sflow:config/oc-sflow:agent-id-ipv6" {
    description
      "Not-supported deviation.";
    deviate not-supported;
  }

  deviation "/oc-sampling:sampling/oc-sflow:sflow/oc-sflow:config/oc-sflow:egress-sampling-rate" {
    description
      "Not-supported deviation.";
    deviate not-supported;
  }

  deviation "/oc-sampling:sampling/oc-sflow:sflow/oc-sflow:config/oc-sflow:polling-interval" {
    description
      "Not-supported deviation.";
    deviate not-supported;
  }

  deviation "/oc-sampling:sampling/oc-sflow:sflow/oc-sflow:interfaces/oc-sflow:interface/oc-sflow:config/oc-sflow:egress-sampling-rate" {
    description
      "Not-supported deviation.";
    deviate not-supported;
  }

  deviation "/oc-sampling:sampling/oc-sflow:sflow/oc-sflow:interfaces/oc-sflow:interface/oc-sflow:config/oc-sflow:ingress-sampling-rate" {
    description
      "Not-supported deviation.";
    deviate not-supported;
  }

  deviation "/oc-sampling:sampling/oc-sflow:sflow/oc-sflow:interfaces/oc-sflow:interface/oc-sflow:config/oc-sflow:polling-interval" {
    description
      "Not-supported deviation.";
    deviate not-supported;
  }

  deviation "/oc-sampling:sampling/oc-sflow:sflow/oc-sflow:interfaces/oc-sflow:interface/oc-sflow:state/oc-sflow:egress-sampling-rate" {
    description
      "Not-supported deviation.";
    deviate not-supported;
  }

  deviation "/oc-sampling:sampling/oc-sflow:sflow/oc-sflow:interfaces/oc-sflow:interface/oc-sflow:state/oc-sflow:ingress-sampling-rate" {
    description
      "Not-supported deviation.";
    deviate not-supported;
  }

  deviation "/oc-sampling:sampling/oc-sflow:sflow/oc-sflow:interfaces/oc-sflow:interface/oc-sflow:state/oc-sflow:packets-sampled" {
    description
      "Not-supported deviation.";
    deviate not-supported;
  }

  deviation "/oc-sampling:sampling/oc-sflow:sflow/oc-sflow:interfaces/oc-sflow:interface/oc-sflow:state/oc-sflow:polling-interval" {
    description
      "Not-supported deviation.";
    deviate not-supported;
  }

  deviation "/oc-sampling:sampling/oc-sflow:sflow/oc-sflow:state/oc-sflow:agent-id-ipv4" {
    description
      "Not-supported deviation.";
    deviate not-supported;
  }

  deviation "/oc-sampling:sampling/oc-sflow:sflow/oc-sflow:state/oc-sflow:agent-id-ipv6" {
    description
      "Not-supported deviation.";
    deviate not-supported;
  }

  deviation "/oc-sampling:sampling/oc-sflow:sflow/oc-sflow:state/oc-sflow:egress-sampling-rate" {
    description
      "Not-supported deviation.";
    deviate not-supported;
  }

  deviation "/oc-sampling:sampling/oc-sflow:sflow/oc-sflow:state/oc-sflow:polling-interval" {
    description
      "Not-supported deviation.";
    deviate not-supported;
  }
}
