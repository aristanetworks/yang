module arista-ebra-octap-agg-port-config {
  yang-version 1;
  namespace "http://arista.com/yang/experimental/eos/arista-ebra-octap-agg-port-config";
  prefix "arista-ebra-octap-agg-port-config";
  
  import openconfig-extensions { prefix "oc-ext"; }
  import openconfig-if-ethernet { prefix "openconfig-if-ethernet"; }
  import openconfig-interfaces { prefix "openconfig-interfaces"; }
  organization
    "Arista Networks <http://arista.com/>";
  contact
    "Arista Networks <http://arista.com/>";
  description
    "Tap Aggregation Port config support
    
    THIS YANG MODULE WAS GENERATED. DO NOT EDIT THIS FILE.";
  
  oc-ext:openconfig-version "1.0.0";
  
  revision "2024-08-12" {
    description
      "Version 1.0.0, generated on 2024-08-12";
    reference "1.0.0";
  }
  
  typedef bridging-open-config-octap-agg-switchport-mode {
    type enumeration {
      enum NON_TAP_TOOL {
        value 0;
        description
          "NON_TAP_TOOL";
      }
      enum TAP {
        value 1;
        description
          "TAP";
      }
      enum TOOL {
        value 2;
        description
          "TOOL";
      }
      enum TAP_TOOL {
        value 3;
        description
          "TAP_TOOL";
      }
    }
    description
      "Tap Aggregation interface modes";
  }
  
  grouping bridging-open-config-ocgroup-name {
    leaf name {
      type string;
      description
        "Tap or Tool group name interface is part of.";
    }
    description
      "Group name";
  }
  
  grouping bridging-open-config-ocgroup-config {
    leaf name {
      type string;
      description
        "Identifier for tap/tool group.";
    }
    container config {
      uses bridging-open-config-ocgroup-name;
      description
        "Group configuration data for interface.";
    }
    container state {
      uses bridging-open-config-ocgroup-name;
      config false;
      description
        "Operational group for interface.";
    }
    description
      "Interface group configuration and operational state";
  }
  
  grouping bridging-open-config-octap-group {
    list tap-group {
      key "name";
      uses bridging-open-config-ocgroup-config;
      description
        "List of tap groups interface is part of.";
    }
    description
      "Grouping for a list of tap group associated with keyed interface";
  }
  
  grouping bridging-open-config-octool-group {
    list tool-group {
      key "name";
      uses bridging-open-config-ocgroup-config;
      description
        "List of tool groups interface is part of.";
    }
    description
      "Grouping for a list of tool group associated with keyed interface";
  }
  
  grouping bridging-open-config-ocmode-config {
    leaf interface-mode {
      type bridging-open-config-octap-agg-switchport-mode;
      description
        "Set the interface to tap, tool or tap-tool mode for configuring interface in tap aggregation mode. For disabling interface in tap aggregation mode, set the interface to NON_TAP_TOOL mode. When the interface is in access, trunk or dot1qTunnel mode for VLANs, tap aggregation interface mode will default to NON_TAP_TOOL mode.";
    }
    description
      "Interface mode configuration";
  }
  
  grouping bridging-open-config-ocswitch-intfs-config {
    leaf name {
      type openconfig-interfaces:interface-id;
      description
        "Identifier for interface.";
    }
    container tap-groups {
      uses bridging-open-config-octap-group;
      description
        "Container for list of tap groups.";
    }
    container tool-groups {
      uses bridging-open-config-octool-group;
      description
        "Container for list of tool groups.";
    }
    container config {
      uses bridging-open-config-ocmode-config;
      description
        "Configuration for tap aggregation interface mode.";
    }
    container state {
      uses bridging-open-config-ocmode-config;
      config false;
      description
        "Operational tap aggregation interface mode.";
    }
    description
      "Interface configuration and operational state data.";
  }
  
  grouping bridging-open-config-ocswitch-intf-config {
    list interface {
      key "name";
      uses bridging-open-config-ocswitch-intfs-config;
      description
        "Tap aggregation configuration for named interfaces on the device.";
    }
    description
      "Top-level grouping for tap aggregation configuration for interfaces.";
  }
  
  augment "/openconfig-interfaces:interfaces/openconfig-interfaces:interface/openconfig-if-ethernet:ethernet" {
    container tap-aggregation {
      uses bridging-open-config-ocswitch-intfs-config;
      description
        "tap-aggregation container";
    }
  }
} // main-yang
