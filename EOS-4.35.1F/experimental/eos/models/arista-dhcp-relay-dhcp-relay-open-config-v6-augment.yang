module arista-dhcp-relay-dhcp-relay-open-config-v6-augment {
  yang-version 1;
  namespace "http://arista.com/yang/experimental/eos/arista-dhcp-relay-dhcp-relay-open-config-v6-augment";
  prefix "arista-dhcp-relay-dhcp-relay-open-config-v6-augment";
  
  import openconfig-extensions { prefix "oc-ext"; }
  import arista-arnet-vrf-name { prefix "arista-arnet-vrf-name"; }
  import openconfig-inet-types { prefix "openconfig-inet-types"; }
  import openconfig-interfaces { prefix "openconfig-interfaces"; }
  import openconfig-relay-agent { prefix "openconfig-relay-agent"; }
  organization
    "Arista Networks <http://arista.com/>";
  contact
    "Arista Networks <http://arista.com/>";
  description
    "Dhcpv6 Relay Model
    
    THIS YANG MODULE WAS GENERATED. DO NOT EDIT THIS FILE.";
  
  oc-ext:openconfig-version "0.0.0";
  
  revision "2024-08-25" {
    description
      "Version 0.0.0, generated on 2024-08-25";
    reference "0.0.0";
  }
  
  typedef ip6-helper-dhcp-relay-open-config-ocdhcp-relay-address-v6 {
    type union {
      type openconfig-inet-types:ipv6-address;
      type string;
    }
    description
      "ip6-helper-dhcp-relay-open-config-ocdhcp-relay-address-v6";
  }
  
  typedef ip6-helper-dhcp-relay-open-config-oc-dhcp-relay-local-address-v6 {
    type union {
      type openconfig-inet-types:ipv6-address;
      type openconfig-interfaces:interface-id;
    }
    description
      "ip6-helper-dhcp-relay-open-config-oc-dhcp-relay-local-address-v6";
  }
  
  grouping ip6-helper-dhcp-relay-open-config-ocdhcp-relay-address-v6-vrf-pair {
    leaf address {
      type ip6-helper-dhcp-relay-open-config-ocdhcp-relay-address-v6;
      description
        "address";
    }
    leaf network-instance {
      type arista-arnet-vrf-name:l3-vrf-name;
      description
        "network-instance";
    }
    description
      "ip6-helper-dhcp-relay-open-config-ocdhcp-relay-address-v6-vrf-pair";
  }
  
  grouping ip6-helper-dhcp-relay-open-config-ocdhcp-relay-intf-key {
    description
      "ip6-helper-dhcp-relay-open-config-ocdhcp-relay-intf-key";
  }
  
  grouping ip6-helper-dhcp-relay-open-config-oc-dhcp-relay-helper-address-v6-config {
    container address-pair {
      uses ip6-helper-dhcp-relay-open-config-ocdhcp-relay-address-v6-vrf-pair;
      description
        "address-pair";
    }
    leaf source-address {
      type ip6-helper-dhcp-relay-open-config-oc-dhcp-relay-local-address-v6;
      description
        "source-address";
    }
    description
      "ip6-helper-dhcp-relay-open-config-oc-dhcp-relay-helper-address-v6-config";
  }
  
  grouping ip6-helper-dhcp-relay-open-config-oc-dhcp-relay-helper-address-v6 {
    uses ip6-helper-dhcp-relay-open-config-ocdhcp-relay-address-v6-vrf-pair;
    container config {
      uses ip6-helper-dhcp-relay-open-config-oc-dhcp-relay-helper-address-v6-config;
      description
        "config";
    }
    container state {
      uses ip6-helper-dhcp-relay-open-config-oc-dhcp-relay-helper-address-v6-config;
      config false;
      description
        "state";
    }
    description
      "ip6-helper-dhcp-relay-open-config-oc-dhcp-relay-helper-address-v6";
  }
  
  grouping ip6-helper-dhcp-relay-open-config-oc-dhcp-relay-helper-addresses-v6 {
    list helper-address {
      key "address network-instance";
      uses ip6-helper-dhcp-relay-open-config-oc-dhcp-relay-helper-address-v6;
      description
        "helper-address";
    }
    description
      "ip6-helper-dhcp-relay-open-config-oc-dhcp-relay-helper-addresses-v6";
  }
  
  grouping ip6-helper-dhcp-relay-open-config-interface-ref-config {
    description
      "ip6-helper-dhcp-relay-open-config-interface-ref-config";
  }
  
  grouping ip6-helper-dhcp-relay-open-config-interface-ref {
    description
      "ip6-helper-dhcp-relay-open-config-interface-ref";
  }
  
  grouping ip6-helper-dhcp-relay-open-config-interface-config {
    description
      "ip6-helper-dhcp-relay-open-config-interface-config";
  }
  
  grouping ip6-helper-dhcp-relay-open-config-ocdhcp-relay-v6-intf {
    container helper-addresses {
      uses ip6-helper-dhcp-relay-open-config-oc-dhcp-relay-helper-addresses-v6;
      description
        "helper-addresses";
    }
    description
      "ip6-helper-dhcp-relay-open-config-ocdhcp-relay-v6-intf";
  }
  
  grouping ip6-helper-dhcp-relay-open-config-ocdhcp-relay-v6 {
    description
      "Dhcp Relay V6 Config";
  }
  
  augment "/openconfig-relay-agent:relay-agent/openconfig-relay-agent:dhcpv6/openconfig-relay-agent:interfaces/openconfig-relay-agent:interface" {
    container helper-addresses {
      uses ip6-helper-dhcp-relay-open-config-oc-dhcp-relay-helper-addresses-v6;
      description
        "helper-addresses";
    }
    description
      "relayAddressesV6Augment";
  }
} // augmented-yang
