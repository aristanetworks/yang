module arista-ale-counters-open-config-pipeline {
  yang-version 1;
  namespace "http://arista.com/yang/experimental/eos/arista-ale-counters-open-config-pipeline";
  prefix "arista-ale-counters-open-config-pipeline";
  
  import openconfig-extensions { prefix "oc-ext"; }
  import arista-ale-counters-open-config-control-plane-traffic-counters { prefix "arista-ale-counters-open-config-control-plane-traffic-counters"; }
  import arista-ale-counters-open-config-hardware-drop-counters { prefix "arista-ale-counters-open-config-hardware-drop-counters"; }
  organization
    "Arista Networks <http://arista.com/>";
  contact
    "Arista Networks <http://arista.com/>";
  description
    "Pipeline counters
    
    THIS YANG MODULE WAS GENERATED. DO NOT EDIT THIS FILE.";
  
  oc-ext:openconfig-version "1.0.0";
  
  revision "2021-10-20" {
    description
      "Version 1.0.0, generated on 2021-10-20";
    reference "1.0.0";
  }
  
  // covered-by: openconfig-platform-pipeline-counters.yang,arista-platform-control-plane-traffic-counters.yang,arista-sand-hardware-drop-counters.yang
  typedef ale-counters-open-config-action {
    type enumeration {
      enum LOG {
        value 0;
        description
          "";
      }
      enum LINECARD_REBOOT {
        value 1;
        description
          "";
      }
      enum LINECARD_OFFLINE {
        value 2;
        description
          "";
      }
      enum NPU_RESET {
        value 3;
        description
          "";
      }
      enum NPU_OFFLINE {
        value 4;
        description
          "";
      }
      enum GET_DIAGNOSTIC_INFO {
        value 5;
        description
          "";
      }
      enum ALARM {
        value 6;
        description
          "";
      }
    }
    description
      "";
  }
  
  typedef ale-counters-open-config-level {
    type enumeration {
      enum FATAL {
        value 0;
        description
          "";
      }
      enum MAJOR {
        value 1;
        description
          "";
      }
      enum MINOR {
        value 2;
        description
          "";
      }
      enum INFORMATIONAL {
        value 3;
        description
          "";
      }
    }
    description
      "";
  }
  
  grouping ale-counters-open-config-pipeline-packet-interface-state {
    leaf in-packets {
      type uint64;
      description
        "";
    }
    leaf out-packets {
      type uint64;
      description
        "";
    }
    leaf in-bytes {
      type uint64;
      description
        "";
    }
    leaf out-bytes {
      type uint64;
      description
        "";
    }
    description
      "";
  }
  
  grouping ale-counters-open-config-pipeline-packet-interface-block {
    container state {
      uses ale-counters-open-config-pipeline-packet-interface-state;
      description
        "";
    }
    description
      "";
  }
  
  grouping ale-counters-open-config-pipeline-packet-lookup-state {
    leaf lookup-utilization {
      type uint8;
      description
        "";
    }
    leaf in-packets {
      type uint64;
      description
        "";
    }
    leaf out-packets {
      type uint64;
      description
        "";
    }
    leaf in-bytes {
      type uint64;
      description
        "";
    }
    leaf out-bytes {
      type uint64;
      description
        "";
    }
    leaf lookup-memory {
      type uint64;
      description
        "";
    }
    leaf lookup-memory-used {
      type uint64;
      description
        "";
    }
    leaf nexthop-memory {
      type uint64;
      description
        "";
    }
    leaf nexthop-memory-used {
      type uint64;
      description
        "";
    }
    leaf acl-memory-total-entries {
      type uint64;
      description
        "";
    }
    leaf acl-memory-used-entries {
      type uint64;
      description
        "";
    }
    leaf acl-memory-total-bytes {
      type uint64;
      description
        "";
    }
    leaf acl-memory-used-bytes {
      type uint64;
      description
        "";
    }
    leaf fragment-total-pkts {
      type uint64;
      description
        "";
    }
    description
      "";
  }
  
  grouping ale-counters-open-config-pipeline-packet-lookup-block {
    container state {
      uses ale-counters-open-config-pipeline-packet-lookup-state;
      description
        "";
    }
    description
      "";
  }
  
  grouping ale-counters-open-config-pipeline-packet-queueing-state {
    leaf in-packets {
      type uint64;
      description
        "";
    }
    leaf out-packets {
      type uint64;
      description
        "";
    }
    leaf in-bytes {
      type uint64;
      description
        "";
    }
    leaf out-bytes {
      type uint64;
      description
        "";
    }
    leaf queue-memory {
      type uint64;
      description
        "";
    }
    leaf queue-memory-used {
      type uint64;
      description
        "";
    }
    leaf loopback-packets {
      type uint64;
      description
        "";
    }
    leaf loopback-bytes {
      type uint64;
      description
        "";
    }
    description
      "";
  }
  
  grouping ale-counters-open-config-pipeline-packet-queueing-block {
    container state {
      uses ale-counters-open-config-pipeline-packet-queueing-state;
      description
        "";
    }
    description
      "";
  }
  
  grouping ale-counters-open-config-pipeline-packet-fabric-state {
    leaf in-cells {
      type uint64;
      description
        "";
    }
    leaf out-cells {
      type uint64;
      description
        "";
    }
    leaf in-packets {
      type uint64;
      description
        "";
    }
    leaf out-packets {
      type uint64;
      description
        "";
    }
    leaf in-bytes {
      type uint64;
      description
        "";
    }
    leaf out-bytes {
      type uint64;
      description
        "";
    }
    leaf in-high-priority-cells {
      type uint64;
      description
        "";
    }
    leaf out-high-priority-cells {
      type uint64;
      description
        "";
    }
    leaf in-low-priority-cells {
      type uint64;
      description
        "";
    }
    leaf out-low-priority-cells {
      type uint64;
      description
        "";
    }
    leaf in-high-priority-packets {
      type uint64;
      description
        "";
    }
    leaf out-high-priority-packets {
      type uint64;
      description
        "";
    }
    leaf in-low-priority-packets {
      type uint64;
      description
        "";
    }
    leaf out-low-priority-packets {
      type uint64;
      description
        "";
    }
    description
      "";
  }
  
  grouping ale-counters-open-config-pipeline-packet-fabric-block {
    container state {
      uses ale-counters-open-config-pipeline-packet-fabric-state;
      description
        "";
    }
    description
      "";
  }
  
  grouping ale-counters-open-config-pipeline-packet-host-state {
    leaf in-packets {
      type uint64;
      description
        "";
    }
    leaf out-packets {
      type uint64;
      description
        "";
    }
    leaf in-bytes {
      type uint64;
      description
        "";
    }
    leaf out-bytes {
      type uint64;
      description
        "";
    }
    leaf fragment-punt-pkts {
      type uint64;
      description
        "";
    }
    leaf in-high-priority-packets {
      type uint64;
      description
        "";
    }
    leaf out-high-priority-packets {
      type uint64;
      description
        "";
    }
    leaf in-low-priority-packets {
      type uint64;
      description
        "";
    }
    leaf out-low-priority-packets {
      type uint64;
      description
        "";
    }
    description
      "";
  }
  
  grouping ale-counters-open-config-pipeline-packet-host-block {
    container state {
      uses ale-counters-open-config-pipeline-packet-host-state;
      description
        "";
    }
    description
      "";
  }
  
  grouping ale-counters-open-config-pipeline-packet-chip-entry {
    container interface-block {
      uses ale-counters-open-config-pipeline-packet-interface-block;
      description
        "";
    }
    container lookup-block {
      uses ale-counters-open-config-pipeline-packet-lookup-block;
      description
        "";
    }
    container queueing-block {
      uses ale-counters-open-config-pipeline-packet-queueing-block;
      description
        "";
    }
    container fabric-block {
      uses ale-counters-open-config-pipeline-packet-fabric-block;
      description
        "";
    }
    container host-interface-block {
      uses ale-counters-open-config-pipeline-packet-host-block;
      description
        "";
    }
    description
      "";
  }
  
  grouping ale-counters-open-config-pipeline-drop-packet-state {
    leaf adverse-aggregate {
      type uint64;
      description
        "";
    }
    leaf congestion-aggregate {
      type uint64;
      description
        "";
    }
    leaf packet-processing-aggregate {
      type uint64;
      description
        "";
    }
    description
      "";
  }
  
  grouping ale-counters-open-config-pipeline-drop-interface-state {
    leaf oversubscription {
      type uint64;
      description
        "";
    }
    leaf in-drops {
      type uint64;
      description
        "";
    }
    leaf out-drops {
      type uint64;
      description
        "";
    }
    description
      "";
  }
  
  grouping ale-counters-open-config-pipeline-drop-interface-block {
    container state {
      uses ale-counters-open-config-pipeline-drop-interface-state;
      description
        "";
    }
    description
      "";
  }
  
  grouping ale-counters-open-config-pipeline-drop-lookup-state {
    leaf oversubscription {
      type uint64;
      description
        "";
    }
    leaf no-route {
      type uint64;
      description
        "";
    }
    leaf no-label {
      type uint64;
      description
        "";
    }
    leaf no-nexthop {
      type uint64;
      description
        "";
    }
    leaf invalid-packet {
      type uint64;
      description
        "";
    }
    leaf forwarding-policy {
      type uint64;
      description
        "";
    }
    leaf incorrect-software-state {
      type uint64;
      description
        "";
    }
    leaf rate-limit {
      type uint64;
      description
        "";
    }
    leaf fragment-total-drops {
      type uint64;
      description
        "";
    }
    leaf lookup-aggregate {
      type uint64;
      description
        "";
    }
    leaf acl-drops {
      type uint64;
      description
        "";
    }
    description
      "";
  }
  
  grouping ale-counters-open-config-pipeline-drop-lookup-block {
    container state {
      uses ale-counters-open-config-pipeline-drop-lookup-state;
      description
        "";
    }
    description
      "";
  }
  
  grouping ale-counters-open-config-pipeline-drop-queueing-state {
    leaf oversubscription {
      type uint64;
      description
        "";
    }
    leaf memory-limit {
      type uint64;
      description
        "";
    }
    leaf incorrect-state {
      type uint64;
      description
        "";
    }
    leaf lookup-queue {
      type uint64;
      description
        "";
    }
    description
      "";
  }
  
  grouping ale-counters-open-config-pipeline-drop-queueing-block {
    container state {
      uses ale-counters-open-config-pipeline-drop-queueing-state;
      description
        "";
    }
    description
      "";
  }
  
  grouping ale-counters-open-config-pipeline-drop-fabric-state {
    leaf oversubscription {
      type uint64;
      description
        "";
    }
    leaf lost-packets {
      type uint64;
      description
        "";
    }
    leaf in-high-priority {
      type uint64;
      description
        "";
    }
    leaf out-high-priority {
      type uint64;
      description
        "";
    }
    leaf in-low-priority {
      type uint64;
      description
        "";
    }
    leaf out-low-priority {
      type uint64;
      description
        "";
    }
    leaf fabric-aggregate {
      type uint64;
      description
        "";
    }
    description
      "";
  }
  
  grouping ale-counters-open-config-pipeline-drop-fabric-block {
    container state {
      uses ale-counters-open-config-pipeline-drop-fabric-state;
      description
        "";
    }
    description
      "";
  }
  
  grouping ale-counters-open-config-pipeline-drop-host-state {
    leaf oversubscription {
      type uint64;
      description
        "";
    }
    leaf rate-limit {
      type uint64;
      description
        "";
    }
    leaf in-high-priority {
      type uint64;
      description
        "";
    }
    leaf out-high-priority {
      type uint64;
      description
        "";
    }
    leaf in-low-priority {
      type uint64;
      description
        "";
    }
    leaf out-low-priority {
      type uint64;
      description
        "";
    }
    leaf fragment-punt {
      type uint64;
      description
        "";
    }
    leaf host-aggregate {
      type uint64;
      description
        "";
    }
    description
      "";
  }
  
  grouping ale-counters-open-config-pipeline-drop-host-block {
    container state {
      uses ale-counters-open-config-pipeline-drop-host-state;
      description
        "";
    }
    description
      "";
  }
  
  grouping ale-counters-open-config-pipeline-drop-chip-entry {
    container state {
      uses ale-counters-open-config-pipeline-drop-packet-state;
      description
        "";
    }
    container interface-block {
      uses ale-counters-open-config-pipeline-drop-interface-block;
      description
        "";
    }
    container lookup-block {
      uses ale-counters-open-config-pipeline-drop-lookup-block;
      description
        "";
    }
    container queueing-block {
      uses ale-counters-open-config-pipeline-drop-queueing-block;
      description
        "";
    }
    container fabric-block {
      uses ale-counters-open-config-pipeline-drop-fabric-block;
      description
        "";
    }
    container host-interface-block {
      uses ale-counters-open-config-pipeline-drop-host-block;
      description
        "";
    }
    container vendor {
      uses arista-ale-counters-open-config-hardware-drop-counters:ale-counters-open-config-pipeline-vendor-hardware-drop-counters;
      description
        "Container for vendor specific drop counters.";
    }
    description
      "";
  }
  
  grouping ale-counters-open-config-pipeline-error-block-entry-state {
    leaf count {
      type uint64;
      description
        "";
    }
    leaf threshold {
      type uint64;
      description
        "";
    }
    leaf action {
      type ale-counters-open-config-action;
      description
        "";
    }
    leaf active {
      type boolean;
      description
        "";
    }
    leaf level {
      type ale-counters-open-config-level;
      description
        "";
    }
    leaf name {
      type string;
      description
        "name of the grouping";
    }
    description
      "";
  }
  
  grouping ale-counters-open-config-pipeline-error-block-entry {
    container state {
      uses ale-counters-open-config-pipeline-error-block-entry-state;
      description
        "";
    }
    leaf name {
      type string;
      description
        "name of the grouping";
    }
    description
      "";
  }
  
  grouping ale-counters-open-config-pipeline-error-interface-block {
    list interface-block-error {
      key "name";
      uses ale-counters-open-config-pipeline-error-block-entry;
      description
        "";
    }
    description
      "";
  }
  
  grouping ale-counters-open-config-pipeline-error-lookup-block {
    list lookup-block-error {
      key "name";
      uses ale-counters-open-config-pipeline-error-block-entry;
      description
        "";
    }
    description
      "";
  }
  
  grouping ale-counters-open-config-pipeline-error-queueing-block {
    list queueing-block-error {
      key "name";
      uses ale-counters-open-config-pipeline-error-block-entry;
      description
        "";
    }
    description
      "";
  }
  
  grouping ale-counters-open-config-pipeline-error-fabric-block {
    list fabric-block-error {
      key "name";
      uses ale-counters-open-config-pipeline-error-block-entry;
      description
        "";
    }
    description
      "";
  }
  
  grouping ale-counters-open-config-pipeline-error-host-interface-block {
    list host-interface-error {
      key "name";
      uses ale-counters-open-config-pipeline-error-block-entry;
      description
        "";
    }
    description
      "";
  }
  
  grouping ale-counters-open-config-pipeline-error-chip-entry {
    container interface-block {
      uses ale-counters-open-config-pipeline-error-interface-block;
      description
        "";
    }
    container lookup-block {
      uses ale-counters-open-config-pipeline-error-lookup-block;
      description
        "";
    }
    container queueing-block {
      uses ale-counters-open-config-pipeline-error-queueing-block;
      description
        "";
    }
    container fabric-block {
      uses ale-counters-open-config-pipeline-error-fabric-block;
      description
        "";
    }
    container host-interface-block {
      uses ale-counters-open-config-pipeline-error-host-interface-block;
      description
        "";
    }
    description
      "";
  }
  
  grouping ale-counters-open-config-pipeline-control-plane-traffic-counters-state {
    leaf queued-aggregate {
      type uint64;
      description
        "";
    }
    leaf queued-bytes-aggregate {
      type uint64;
      description
        "";
    }
    leaf dropped-aggregate {
      type uint64;
      description
        "";
    }
    leaf dropped-bytes-aggregate {
      type uint64;
      description
        "";
    }
    description
      "";
  }
  
  grouping ale-counters-open-config-pipeline-control-plane-traffic {
    container state {
      uses ale-counters-open-config-pipeline-control-plane-traffic-counters-state;
      description
        "State container for control-plane traffic counters.";
    }
    container vendor {
      uses arista-ale-counters-open-config-control-plane-traffic-counters:ale-counters-open-config-pipeline-vendor-control-plane-traffic-counters;
      description
        "Container for vendor-specific control-plane traffic counters.";
    }
    description
      "Counters that are related to traffic destined to the control-plane.";
  }
  
  grouping ale-counters-open-config-pipeline-counters {
    container packet {
      uses ale-counters-open-config-pipeline-packet-chip-entry;
      description
        "";
    }
    container drop {
      uses ale-counters-open-config-pipeline-drop-chip-entry;
      description
        "";
    }
    container errors {
      uses ale-counters-open-config-pipeline-error-chip-entry;
      description
        "";
    }
    container control-plane-traffic {
      uses ale-counters-open-config-pipeline-control-plane-traffic;
      description
        "Counters that are related to traffic destined to the control-plane.";
    }
    leaf name {
      type string;
      description
        "name of the grouping";
    }
    description
      "";
  }
  
  grouping ale-counters-open-config-pipeline {
    list pipeline-counters {
      key "name";
      uses ale-counters-open-config-pipeline-counters;
      description
        "";
    }
    leaf name {
      type string;
      description
        "name of the grouping";
    }
    description
      "";
  }
  
  container components {
    list component {
      key "name";
      oc-ext:telemetry-atomic;
      leaf name {
        type string;
        description
          "name leaf used as key for component list";
      }
      container integrated-circuit {
        container pipeline-counters {
          config false;
          uses ale-counters-open-config-pipeline-counters;
          description
            "pipeline-counters container";
        }
        oc-ext:telemetry-atomic;
        description
          "integrated-circuit container";
      }
      oc-ext:telemetry-atomic;
      description
        "component list";
    }
    oc-ext:telemetry-atomic;
    description
      "components container";
  }
} // main-yang
