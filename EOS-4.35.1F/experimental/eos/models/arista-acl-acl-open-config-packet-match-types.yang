module arista-acl-acl-open-config-packet-match-types {
  yang-version 1;
  namespace "http://arista.com/yang/experimental/eos/arista-acl-acl-open-config-packet-match-types";
  prefix "arista-acl-acl-open-config-packet-match-types";
  
  import openconfig-extensions { prefix "oc-ext"; }
  import openconfig-acl { prefix "openconfig-acl"; }
  import openconfig-packet-match-types { prefix "openconfig-packet-match-types"; }
  organization
    "Arista Networks <http://arista.com/>";
  contact
    "Arista Networks <http://arista.com/>";
  description
    "External tac model for traffic policy
    
    THIS YANG MODULE WAS GENERATED. DO NOT EDIT THIS FILE.";
  
  oc-ext:openconfig-version "1.0.0";
  
  revision "2024-08-19" {
    description
      "Version 1.0.0, generated on 2024-08-19";
    reference "1.0.0";
  }
  
  // covered-by: openconfig-packet-match-types.yang, openconfig-acl.yang
  typedef acl-open-config-ethertype-num {
    type uint16;
    description
      "acl-open-config-ethertype-num";
  }
  
  typedef acl-open-config-explicit-detail-mode {
    type enumeration {
      enum ANY {
        value 0;
        description
          "ANY";
      }
      enum ALL {
        value 1;
        description
          "ALL";
      }
    }
    description
      "acl-open-config-explicit-detail-mode";
  }
  
  typedef acl-open-config-detail-mode {
    type enumeration {
      enum EXPLICIT {
        value 0;
        description
          "EXPLICIT_MODE";
      }
      enum BUILTIN {
        value 1;
        description
          "BUILTIN_MODE";
      }
    }
    description
      "acl-open-config-detail-mode";
  }
  
  typedef acl-open-config-builtin-detail {
    type enumeration {
      enum TCP_INITIAL {
        value 0;
        description
          "TCP_INITIAL";
      }
      enum TCP_ESTABLISHED {
        value 1;
        description
          "TCP_ESTABLISHED";
      }
      enum FRAGMENT {
        value 2;
        description
          "FRAGMENT";
      }
    }
    description
      "acl-open-config-builtin-detail";
  }
  
  typedef acl-open-config-port-enumns-port-enum {
    type enumeration {
      enum ANY {
        value 0;
        description
          "ANY";
      }
    }
    description
      "acl-open-config-port-enumns-port-enum";
  }
  
} // main-yang
