module arista-pfc-history-counters-augment {
  yang-version 1;
  namespace "http://arista.com/yang/experimental/eos/arista-pfc-history-counters-augment";
  prefix "arista-pfc-history-counters-augment";
  
  import openconfig-extensions { prefix "oc-ext"; }
  import arista-intf-augments { prefix "arista-intf-augments"; }
  import openconfig-if-ethernet { prefix "openconfig-if-ethernet"; }
  import openconfig-interfaces { prefix "openconfig-interfaces"; }
  import openconfig-types { prefix "openconfig-types"; }
  organization
    "Arista Networks <http://arista.com/>";
  contact
    "Arista Networks <http://arista.com/>";
  description
    "This module contains priority-flow-control (PFC) history counters.
    
    THIS YANG MODULE WAS GENERATED. DO NOT EDIT THIS FILE.";
  
  oc-ext:openconfig-version "1.0.0";
  
  revision "2025-05-11" {
    description
      "Version 1.0.0, generated on 2025-05-11";
    reference "1.0.0";
  }
  
  grouping ale-counters-open-config-pfc-history-counter-key {
    description
      "ale-counters-open-config-pfc-history-counter-key";
  }
  
  grouping ale-counters-open-config-pfc-history-counter {
    leaf pfc-on-max-rx-time {
      type uint64;
      description
        "The maximum time in nanoseconds that (interface, priority) was paused.";
    }
    leaf pfc-on-total-rx-time {
      type uint64;
      description
        "The total time in nanoseconds that (interface, priority) was paused.";
    }
    leaf rx-transitions {
      type uint64;
      description
        "The total number of times a given (interface, priority) transitioned from being available for sending traffic to being paused.";
    }
    leaf max-rx-timestamp {
      type openconfig-types:timeticks64;
      description
        "The timestamp at which the \"Max RX on time\" was seen.";
      }
      description
        "ale-counters-open-config-pfc-history-counter";
    }
    
    grouping ale-counters-open-config-interface-pfc-history-counters {
      description
        "ale-counters-open-config-interface-pfc-history-counters";
    }
    
    augment "/openconfig-interfaces:interfaces/openconfig-interfaces:interface/openconfig-if-ethernet:ethernet/arista-intf-augments:pfc/arista-intf-augments:priorities/arista-intf-augments:priority/arista-intf-augments:state" {
      leaf pfc-on-max-rx-time {
        type uint64;
        description
          "The maximum time in nanoseconds that (interface, priority) was paused.";
      }
      leaf pfc-on-total-rx-time {
        type uint64;
        description
          "The total time in nanoseconds that (interface, priority) was paused.";
      }
      leaf rx-transitions {
        type uint64;
        description
          "The total number of times a given (interface, priority) transitioned from being available for sending traffic to being paused.";
      }
      leaf max-rx-timestamp {
        type openconfig-types:timeticks64;
        description
          "The timestamp at which the \"Max RX on time\" was seen.";
        }
        description
          "The maximum time in nanoseconds that (interface, priority) was paused.
          The total time in nanoseconds that (interface, priority) was paused.
          The total number of times a given (interface, priority) transitioned from being available for sending traffic to being paused.
          The timestamp at which the \"Max RX on time\" was seen.";
        }
      } // augmented-yang
