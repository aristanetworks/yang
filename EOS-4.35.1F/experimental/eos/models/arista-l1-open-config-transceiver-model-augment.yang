module arista-l1-open-config-transceiver-model-augment {
  yang-version 1;
  namespace "http://arista.com/yang/experimental/eos/arista-l1-open-config-transceiver-model-augment";
  prefix "arista-l1-open-config-transceiver-model-augment";
  
  import openconfig-extensions { prefix "oc-ext"; }
  import arista-l1-open-config-xcvr-oc-types { prefix "arista-l1-open-config-xcvr-oc-types"; }
  import openconfig-platform { prefix "openconfig-platform"; }
  import openconfig-platform-transceiver { prefix "openconfig-platform-transceiver"; }
  import openconfig-transport-types { prefix "openconfig-transport-types"; }
  organization
    "Arista Networks <http://arista.com/>";
  contact
    "Arista Networks <http://arista.com/>";
  description
    "Attributes related to transceiver components
    
    THIS YANG MODULE WAS GENERATED. DO NOT EDIT THIS FILE.";
  
  oc-ext:openconfig-version "1.0.0";
  
  revision "2022-05-12" {
    description
      "Version 1.0.0, generated on 2022-05-12";
    reference "1.0.0";
  }
  
  grouping l1-open-config-xcvr-transceiver-config {
    description
      "Container for the config of a transceiver";
  }
  
  grouping l1-open-config-xcvr-transceiver-config-base {
    description
      "Config container for the transceiver attributes";
  }
  
  grouping l1-open-config-xcvr-physical-channel-index {
    description
      "Index for a physical channel (lane) inside the transceiver";
  }
  
  grouping l1-open-config-xcvr-physical-channel-config {
    description
      "Container for the config of a physical channel";
  }
  
  grouping l1-open-config-xcvr-physical-channel-config-base {
    description
      "Container for the lane-base config of the transceiver";
  }
  
  grouping l1-open-config-xcvr-transceiver-state {
    container booster-output-power {
      uses arista-l1-open-config-xcvr-oc-types:l1-open-config-xcvr-instant-stats;
      description
        "The line system egress path output power.";
    }
    container booster-input-power {
      uses arista-l1-open-config-xcvr-oc-types:l1-open-config-xcvr-instant-stats;
      description
        "The line system egress path input power.";
    }
    container pre-amp-output-power {
      uses arista-l1-open-config-xcvr-oc-types:l1-open-config-xcvr-instant-stats;
      description
        "The line system ingress path output power.";
    }
    container pre-amp-input-power {
      uses arista-l1-open-config-xcvr-oc-types:l1-open-config-xcvr-instant-stats;
      description
        "The line system ingress path input power.";
    }
    description
      "Container for the state of the transceiver";
  }
  
  grouping l1-open-config-xcvr-transceiver-thresholds-index {
    description
      "Index for a dom threshold at the specified severity level";
  }
  
  grouping l1-open-config-xcvr-transceiver-thresholds-state {
    description
      "Container for all the threshold attributes";
  }
  
  grouping l1-open-config-xcvr-physical-channel-state {
    description
      "Container for the lane-based state of the transceiver";
  }
  
  grouping l1-open-config-xcvr-transceiver-thresholds-type {
    description
      "Container for dom thresholds with severity as specified in the key";
  }
  
  grouping l1-open-config-xcvr-transceiver-thresholds {
    description
      "Container for all thresholds";
  }
  
  grouping l1-open-config-xcvr-physical-channel {
    description
      "Container for lane-based transceiver state";
  }
  
  grouping l1-open-config-xcvr-transceiver {
    description
      "Container for the base transceiver component";
  }
  
  grouping l1-open-config-xcvr-host-lane-key {
    description
      "l1-open-config-xcvr-host-lane-key";
  }
  
  grouping l1-open-config-xcvr-host-lane-config {
    description
      "l1-open-config-xcvr-host-lane-config";
  }
  
  grouping l1-open-config-xcvr-host-lane-state {
    description
      "l1-open-config-xcvr-host-lane-state";
  }
  
  grouping l1-open-config-xcvr-host-lane-entry {
    description
      "l1-open-config-xcvr-host-lane-entry";
  }
  
  grouping l1-open-config-xcvr-host-lane {
    description
      "l1-open-config-xcvr-host-lane";
  }
  
  augment "/openconfig-platform:components/openconfig-platform:component/openconfig-platform-transceiver:transceiver/openconfig-platform-transceiver:state" {
    container booster-output-power {
      uses arista-l1-open-config-xcvr-oc-types:l1-open-config-xcvr-instant-stats;
      description
        "The line system egress path output power.";
    }
    container booster-input-power {
      uses arista-l1-open-config-xcvr-oc-types:l1-open-config-xcvr-instant-stats;
      description
        "The line system egress path input power.";
    }
    container pre-amp-output-power {
      uses arista-l1-open-config-xcvr-oc-types:l1-open-config-xcvr-instant-stats;
      description
        "The line system ingress path output power.";
    }
    container pre-amp-input-power {
      uses arista-l1-open-config-xcvr-oc-types:l1-open-config-xcvr-instant-stats;
      description
        "The line system ingress path input power.";
    }
    description
      "boosterOutputPower
      boosterInputPower
      preAmpOutputPower
      preAmpInputPower";
  }
} // augmented-yang
