module arista-local-routing-deviations {
  namespace "http://arista.com/yang/openconfig/local-routing/deviations";
  prefix arista-local-routing-deviations;

  import openconfig-network-instance {
    prefix oc-netinst;
  }

  organization
    "Arista Networks, Inc.";
  contact
    "Arista Networks, Inc.
     Product Support";
  description
    "This module contains OpenConfig local-routing deviations in Arista EOS.
     
     Copyright (c) 2017 Arista Networks, Inc. All rights reserved.";

  revision 2017-11-22 {
    description
      "Initial deviations file.";
  }

  deviation "/oc-netinst:network-instances/oc-netinst:network-instance/oc-netinst:protocols/oc-netinst:protocol/oc-netinst:static-routes/oc-netinst:static/oc-netinst:next-hops/oc-netinst:next-hop/oc-netinst:config/oc-netinst:recurse" {
    description
      "configuring recurse is not supported by EOS";
    deviate not-supported;
  }
  deviation "/oc-netinst:network-instances/oc-netinst:network-instance/oc-netinst:protocols/oc-netinst:protocol/oc-netinst:static-routes/oc-netinst:static/oc-netinst:next-hops/oc-netinst:next-hop/oc-netinst:state/oc-netinst:recurse" {
    description
      "configuring recurse is not supported by EOS";
    deviate not-supported;
  }
  deviation "/oc-netinst:network-instances/oc-netinst:network-instance/oc-netinst:protocols/oc-netinst:protocol/oc-netinst:static-routes/oc-netinst:static/oc-netinst:next-hops/oc-netinst:next-hop/oc-netinst:config/oc-netinst:metric" {
    description
      "metric EOS range restriction. metric for static routes corresponds to their administrative distance in EOS";
    deviate replace {
      type uint32 {
        range "1..255";
      }
    }
  }
  deviation "/oc-netinst:network-instances/oc-netinst:network-instance/oc-netinst:protocols/oc-netinst:protocol/oc-netinst:static-routes/oc-netinst:static/oc-netinst:next-hops/oc-netinst:next-hop/oc-netinst:state/oc-netinst:metric" {
    description
      "metric EOS range restriction. metric for static routes corresponds to their administrative distance in EOS";
    deviate replace {
      type uint32 {
        range "1..255";
      }
    }
  }
  deviation "/oc-netinst:network-instances/oc-netinst:network-instance/oc-netinst:protocols/oc-netinst:protocol/oc-netinst:static-routes/oc-netinst:static/oc-netinst:next-hops/oc-netinst:next-hop/oc-netinst:interface-ref/oc-netinst:config/oc-netinst:subinterface" {
    description
      "subinterface next-hop currently not supported";
    deviate not-supported;
  }
  deviation "/oc-netinst:network-instances/oc-netinst:network-instance/oc-netinst:protocols/oc-netinst:protocol/oc-netinst:static-routes/oc-netinst:static/oc-netinst:next-hops/oc-netinst:next-hop/oc-netinst:interface-ref/oc-netinst:state/oc-netinst:subinterface" {
    description
      "subinterface next-hop currently not supported";
    deviate not-supported;
  }
  deviation "/oc-netinst:network-instances/oc-netinst:network-instance/oc-netinst:protocols/oc-netinst:protocol/oc-netinst:static-routes/oc-netinst:static/oc-netinst:next-hops/oc-netinst:next-hop/oc-netinst:interface-ref/oc-netinst:config/oc-netinst:interface" {
    description
      "change type from leafref to string: temporary fix until vlan interfaces are mapped";
    deviate replace {
      type string;
    }
  }
  deviation "/oc-netinst:network-instances/oc-netinst:network-instance/oc-netinst:protocols/oc-netinst:protocol/oc-netinst:static-routes/oc-netinst:static/oc-netinst:next-hops/oc-netinst:next-hop/oc-netinst:interface-ref/oc-netinst:state/oc-netinst:interface" {
    description
      "change type from leafref to string: temporary fix until vlan interfaces are mapped";
    deviate replace {
      type string;
    }
  }
}
