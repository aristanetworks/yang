module arista-system-deviations {
  namespace "http://arista.com/yang/openconfig/system/deviations";
  prefix arista-system-deviations;

  organization
    "Arista Networks, Inc.";
  contact
    "Arista Networks, Inc.
     Product Support";
  description
    "This module contains OpenConfig system deviations in Arista EOS.
     Copyright (c) 2017 Arista Networks, Inc. All rights reserved.";

  revision 2017-09-24 {
    description
      "Initial deviations file.";
  }
}
