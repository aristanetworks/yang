module arista-srte-augments {
  namespace "http://arista.com/yang/openconfig/policy-forwarding/augments";
  prefix arista-srte-augments;

  import openconfig-network-instance {
    prefix oc-netinst;
  }
  import openconfig-pf-srte {
    prefix oc-pf-srte;
  }

  organization
    "Arista Networks, Inc.";
  contact
    "Arista Networks, Inc.
    Product Support";
  description
    "This module contains OpenConfig SRTE deviations in Arista EOS.

    Copyright (c) 2019 Arista Networks, Inc. All rights reserved.";

  revision 2019-08-07 {
    description
      "Initial augment file.";
  }

  typedef explicit-null-label-type {
    type enumeration {
      enum IPV4 {
        description
          "Push an IPv4 Explicit NULL label on an unlabeled IPv4 packet";
      }
      enum IPV6 {
        description
          "Push an IPv6 Explicit NULL label on an unlabeled IPv6 packet";
      }
      enum IPV4_IPV6 {
        description
          "Push an IPv4 Explicit NULL label on an unlabeled IPv4 packet;
          Push an IPv6 Explicit NULL label on an unlabeled IPv6 packet";
      }
      enum NONE {
        description
          "No Explicit NULL label will be pushed for both IPv4 and IPv6
          unlabeled packets";
      }
    }
  }

  augment "/oc-netinst:network-instances/oc-netinst:network-instance/oc-netinst:policy-forwarding/oc-netinst:policies/oc-netinst:policy/oc-netinst:rules/oc-netinst:rule/oc-pf-srte:srte/oc-pf-srte:config" {
    leaf explicit-null-label {
      type explicit-null-label-type;
      description
        "Type of explicit null label that is being pushed on an unlabeled
        IP packet. If unspecified, the behaviour of the system is undefined,
        and is subject to local implementation choice.";
      reference
        "draft-ietf-idr-segment-routing-te-policy - Section 2.4.4";
    }
  }

  augment "/oc-netinst:network-instances/oc-netinst:network-instance/oc-netinst:policy-forwarding/oc-netinst:policies/oc-netinst:policy/oc-netinst:rules/oc-netinst:rule/oc-pf-srte:srte/oc-pf-srte:state" {
    leaf explicit-null-label {
      type explicit-null-label-type;
      description
        "Type of explicit null label that is being pushed on an unlabeled
        IP packet. If unspecified, the behaviour of the system is undefined,
        and is subject to local implementation choice.";
      reference
        "draft-ietf-idr-segment-routing-te-policy - Section 2.4.4";
    }
  }
}
