module arista-terminal-device-notsupported-deviations {
  namespace "http://arista.com/yang/openconfig/terminal-device/notsupported-deviations";
  prefix arista-terminal-device-notsupported-deviations;

  import openconfig-terminal-device {
    prefix oc-opt-term;
  }

  organization
    "Arista Networks, Inc.";
  contact
    "Arista Networks, Inc.
     Product Support";
  description
    "This module contains OpenConfig terminal-device deviations in Arista EOS.
     Copyright (c) 2022 Arista Networks, Inc. All rights reserved.";

  revision 2022-05-25 {
    description
      "Not-supported deviations file.";
  }

  deviation "/oc-opt-term:terminal-device" {
    description
      "Not-supported deviation.";
    deviate not-supported;
  }
}
