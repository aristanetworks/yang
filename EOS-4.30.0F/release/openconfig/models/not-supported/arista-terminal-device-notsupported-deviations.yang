module arista-terminal-device-notsupported-deviations {
  namespace "http://arista.com/yang/openconfig/terminal-device/notsupported-deviations";
  prefix arista-terminal-device-notsupported-deviations;

  import openconfig-terminal-device {
    prefix oc-opt-term;
  }

  organization
    "Arista Networks, Inc.";
  contact
    "Arista Networks, Inc.
     Product Support";
  description
    "This module contains OpenConfig terminal-device deviations in Arista EOS.
     Copyright (c) 2020 Arista Networks, Inc. All rights reserved.";

  revision 2022-12-19 {
    description
      "Auto-generated not-supported deviations for unsupported paths";
  }

  deviation "/oc-opt-term:terminal-device/oc-opt-term:config" {
    description
      "Not-supported deviation.";
    deviate not-supported;
  }

  deviation "/oc-opt-term:terminal-device/oc-opt-term:operational-modes" {
    description
      "Not-supported deviation.";
    deviate not-supported;
  }

  deviation "/oc-opt-term:terminal-device/oc-opt-term:state" {
    description
      "Not-supported deviation.";
    deviate not-supported;
  }

  deviation "/oc-opt-term:terminal-device/oc-opt-term:logical-channels/oc-opt-term:channel/oc-opt-term:config" {
    description
      "Not-supported deviation.";
    deviate not-supported;
  }

  deviation "/oc-opt-term:terminal-device/oc-opt-term:logical-channels/oc-opt-term:channel/oc-opt-term:otn" {
    description
      "Not-supported deviation.";
    deviate not-supported;
  }

  deviation "/oc-opt-term:terminal-device/oc-opt-term:logical-channels/oc-opt-term:channel/oc-opt-term:ethernet/oc-opt-term:config" {
    description
      "Not-supported deviation.";
    deviate not-supported;
  }

  deviation "/oc-opt-term:terminal-device/oc-opt-term:logical-channels/oc-opt-term:channel/oc-opt-term:ethernet/oc-opt-term:lldp" {
    description
      "Not-supported deviation.";
    deviate not-supported;
  }

  deviation "/oc-opt-term:terminal-device/oc-opt-term:logical-channels/oc-opt-term:channel/oc-opt-term:ethernet/oc-opt-term:state/oc-opt-term:als-delay" {
    description
      "Not-supported deviation.";
    deviate not-supported;
  }

  deviation "/oc-opt-term:terminal-device/oc-opt-term:logical-channels/oc-opt-term:channel/oc-opt-term:ethernet/oc-opt-term:state/oc-opt-term:client-als" {
    description
      "Not-supported deviation.";
    deviate not-supported;
  }

  deviation "/oc-opt-term:terminal-device/oc-opt-term:logical-channels/oc-opt-term:channel/oc-opt-term:ethernet/oc-opt-term:state/oc-opt-term:esnr" {
    description
      "Not-supported deviation.";
    deviate not-supported;
  }

  deviation "/oc-opt-term:terminal-device/oc-opt-term:logical-channels/oc-opt-term:channel/oc-opt-term:ethernet/oc-opt-term:state/oc-opt-term:in-8021q-frames" {
    description
      "Not-supported deviation.";
    deviate not-supported;
  }

  deviation "/oc-opt-term:terminal-device/oc-opt-term:logical-channels/oc-opt-term:channel/oc-opt-term:ethernet/oc-opt-term:state/oc-opt-term:in-block-errors" {
    description
      "Not-supported deviation.";
    deviate not-supported;
  }

  deviation "/oc-opt-term:terminal-device/oc-opt-term:logical-channels/oc-opt-term:channel/oc-opt-term:ethernet/oc-opt-term:state/oc-opt-term:in-carrier-errors" {
    description
      "Not-supported deviation.";
    deviate not-supported;
  }

  deviation "/oc-opt-term:terminal-device/oc-opt-term:logical-channels/oc-opt-term:channel/oc-opt-term:ethernet/oc-opt-term:state/oc-opt-term:in-crc-errors" {
    description
      "Not-supported deviation.";
    deviate not-supported;
  }

  deviation "/oc-opt-term:terminal-device/oc-opt-term:logical-channels/oc-opt-term:channel/oc-opt-term:ethernet/oc-opt-term:state/oc-opt-term:in-fragment-frames" {
    description
      "Not-supported deviation.";
    deviate not-supported;
  }

  deviation "/oc-opt-term:terminal-device/oc-opt-term:logical-channels/oc-opt-term:channel/oc-opt-term:ethernet/oc-opt-term:state/oc-opt-term:in-interrupted-tx" {
    description
      "Not-supported deviation.";
    deviate not-supported;
  }

  deviation "/oc-opt-term:terminal-device/oc-opt-term:logical-channels/oc-opt-term:channel/oc-opt-term:ethernet/oc-opt-term:state/oc-opt-term:in-jabber-frames" {
    description
      "Not-supported deviation.";
    deviate not-supported;
  }

  deviation "/oc-opt-term:terminal-device/oc-opt-term:logical-channels/oc-opt-term:channel/oc-opt-term:ethernet/oc-opt-term:state/oc-opt-term:in-late-collision" {
    description
      "Not-supported deviation.";
    deviate not-supported;
  }

  deviation "/oc-opt-term:terminal-device/oc-opt-term:logical-channels/oc-opt-term:channel/oc-opt-term:ethernet/oc-opt-term:state/oc-opt-term:in-mac-control-frames" {
    description
      "Not-supported deviation.";
    deviate not-supported;
  }

  deviation "/oc-opt-term:terminal-device/oc-opt-term:logical-channels/oc-opt-term:channel/oc-opt-term:ethernet/oc-opt-term:state/oc-opt-term:in-mac-errors-rx" {
    description
      "Not-supported deviation.";
    deviate not-supported;
  }

  deviation "/oc-opt-term:terminal-device/oc-opt-term:logical-channels/oc-opt-term:channel/oc-opt-term:ethernet/oc-opt-term:state/oc-opt-term:in-mac-pause-frames" {
    description
      "Not-supported deviation.";
    deviate not-supported;
  }

  deviation "/oc-opt-term:terminal-device/oc-opt-term:logical-channels/oc-opt-term:channel/oc-opt-term:ethernet/oc-opt-term:state/oc-opt-term:in-maxsize-exceeded" {
    description
      "Not-supported deviation.";
    deviate not-supported;
  }

  deviation "/oc-opt-term:terminal-device/oc-opt-term:logical-channels/oc-opt-term:channel/oc-opt-term:ethernet/oc-opt-term:state/oc-opt-term:in-oversize-frames" {
    description
      "Not-supported deviation.";
    deviate not-supported;
  }

  deviation "/oc-opt-term:terminal-device/oc-opt-term:logical-channels/oc-opt-term:channel/oc-opt-term:ethernet/oc-opt-term:state/oc-opt-term:in-pcs-bip-errors" {
    description
      "Not-supported deviation.";
    deviate not-supported;
  }

  deviation "/oc-opt-term:terminal-device/oc-opt-term:logical-channels/oc-opt-term:channel/oc-opt-term:ethernet/oc-opt-term:state/oc-opt-term:in-pcs-errored-seconds" {
    description
      "Not-supported deviation.";
    deviate not-supported;
  }

  deviation "/oc-opt-term:terminal-device/oc-opt-term:logical-channels/oc-opt-term:channel/oc-opt-term:ethernet/oc-opt-term:state/oc-opt-term:in-pcs-severely-errored-seconds" {
    description
      "Not-supported deviation.";
    deviate not-supported;
  }

  deviation "/oc-opt-term:terminal-device/oc-opt-term:logical-channels/oc-opt-term:channel/oc-opt-term:ethernet/oc-opt-term:state/oc-opt-term:in-pcs-unavailable-seconds" {
    description
      "Not-supported deviation.";
    deviate not-supported;
  }

  deviation "/oc-opt-term:terminal-device/oc-opt-term:logical-channels/oc-opt-term:channel/oc-opt-term:ethernet/oc-opt-term:state/oc-opt-term:in-single-collision" {
    description
      "Not-supported deviation.";
    deviate not-supported;
  }

  deviation "/oc-opt-term:terminal-device/oc-opt-term:logical-channels/oc-opt-term:channel/oc-opt-term:ethernet/oc-opt-term:state/oc-opt-term:in-symbol-error" {
    description
      "Not-supported deviation.";
    deviate not-supported;
  }

  deviation "/oc-opt-term:terminal-device/oc-opt-term:logical-channels/oc-opt-term:channel/oc-opt-term:ethernet/oc-opt-term:state/oc-opt-term:in-undersize-frames" {
    description
      "Not-supported deviation.";
    deviate not-supported;
  }

  deviation "/oc-opt-term:terminal-device/oc-opt-term:logical-channels/oc-opt-term:channel/oc-opt-term:ethernet/oc-opt-term:state/oc-opt-term:out-8021q-frames" {
    description
      "Not-supported deviation.";
    deviate not-supported;
  }

  deviation "/oc-opt-term:terminal-device/oc-opt-term:logical-channels/oc-opt-term:channel/oc-opt-term:ethernet/oc-opt-term:state/oc-opt-term:out-block-errors" {
    description
      "Not-supported deviation.";
    deviate not-supported;
  }

  deviation "/oc-opt-term:terminal-device/oc-opt-term:logical-channels/oc-opt-term:channel/oc-opt-term:ethernet/oc-opt-term:state/oc-opt-term:out-crc-errors" {
    description
      "Not-supported deviation.";
    deviate not-supported;
  }

  deviation "/oc-opt-term:terminal-device/oc-opt-term:logical-channels/oc-opt-term:channel/oc-opt-term:ethernet/oc-opt-term:state/oc-opt-term:out-mac-control-frames" {
    description
      "Not-supported deviation.";
    deviate not-supported;
  }

  deviation "/oc-opt-term:terminal-device/oc-opt-term:logical-channels/oc-opt-term:channel/oc-opt-term:ethernet/oc-opt-term:state/oc-opt-term:out-mac-errors-tx" {
    description
      "Not-supported deviation.";
    deviate not-supported;
  }

  deviation "/oc-opt-term:terminal-device/oc-opt-term:logical-channels/oc-opt-term:channel/oc-opt-term:ethernet/oc-opt-term:state/oc-opt-term:out-mac-pause-frames" {
    description
      "Not-supported deviation.";
    deviate not-supported;
  }

  deviation "/oc-opt-term:terminal-device/oc-opt-term:logical-channels/oc-opt-term:channel/oc-opt-term:ethernet/oc-opt-term:state/oc-opt-term:out-pcs-bip-errors" {
    description
      "Not-supported deviation.";
    deviate not-supported;
  }

  deviation "/oc-opt-term:terminal-device/oc-opt-term:logical-channels/oc-opt-term:channel/oc-opt-term:ethernet/oc-opt-term:state/oc-opt-term:post-fec-ber" {
    description
      "Not-supported deviation.";
    deviate not-supported;
  }

  deviation "/oc-opt-term:terminal-device/oc-opt-term:logical-channels/oc-opt-term:channel/oc-opt-term:ethernet/oc-opt-term:state/oc-opt-term:q-value" {
    description
      "Not-supported deviation.";
    deviate not-supported;
  }

  deviation "/oc-opt-term:terminal-device/oc-opt-term:logical-channels/oc-opt-term:channel/oc-opt-term:ethernet/oc-opt-term:state/oc-opt-term:pre-fec-ber/oc-opt-term:avg" {
    description
      "Not-supported deviation.";
    deviate not-supported;
  }

  deviation "/oc-opt-term:terminal-device/oc-opt-term:logical-channels/oc-opt-term:channel/oc-opt-term:ethernet/oc-opt-term:state/oc-opt-term:pre-fec-ber/oc-opt-term:interval" {
    description
      "Not-supported deviation.";
    deviate not-supported;
  }

  deviation "/oc-opt-term:terminal-device/oc-opt-term:logical-channels/oc-opt-term:channel/oc-opt-term:ethernet/oc-opt-term:state/oc-opt-term:pre-fec-ber/oc-opt-term:max" {
    description
      "Not-supported deviation.";
    deviate not-supported;
  }

  deviation "/oc-opt-term:terminal-device/oc-opt-term:logical-channels/oc-opt-term:channel/oc-opt-term:ethernet/oc-opt-term:state/oc-opt-term:pre-fec-ber/oc-opt-term:max-time" {
    description
      "Not-supported deviation.";
    deviate not-supported;
  }

  deviation "/oc-opt-term:terminal-device/oc-opt-term:logical-channels/oc-opt-term:channel/oc-opt-term:ethernet/oc-opt-term:state/oc-opt-term:pre-fec-ber/oc-opt-term:min" {
    description
      "Not-supported deviation.";
    deviate not-supported;
  }

  deviation "/oc-opt-term:terminal-device/oc-opt-term:logical-channels/oc-opt-term:channel/oc-opt-term:ethernet/oc-opt-term:state/oc-opt-term:pre-fec-ber/oc-opt-term:min-time" {
    description
      "Not-supported deviation.";
    deviate not-supported;
  }

  deviation "/oc-opt-term:terminal-device/oc-opt-term:logical-channels/oc-opt-term:channel/oc-opt-term:ingress/oc-opt-term:config" {
    description
      "Not-supported deviation.";
    deviate not-supported;
  }

  deviation "/oc-opt-term:terminal-device/oc-opt-term:logical-channels/oc-opt-term:channel/oc-opt-term:logical-channel-assignments/oc-opt-term:assignment/oc-opt-term:config" {
    description
      "Not-supported deviation.";
    deviate not-supported;
  }

  deviation "/oc-opt-term:terminal-device/oc-opt-term:logical-channels/oc-opt-term:channel/oc-opt-term:logical-channel-assignments/oc-opt-term:assignment/oc-opt-term:state/oc-opt-term:allocation" {
    description
      "Not-supported deviation.";
    deviate not-supported;
  }

  deviation "/oc-opt-term:terminal-device/oc-opt-term:logical-channels/oc-opt-term:channel/oc-opt-term:logical-channel-assignments/oc-opt-term:assignment/oc-opt-term:state/oc-opt-term:description" {
    description
      "Not-supported deviation.";
    deviate not-supported;
  }

  deviation "/oc-opt-term:terminal-device/oc-opt-term:logical-channels/oc-opt-term:channel/oc-opt-term:logical-channel-assignments/oc-opt-term:assignment/oc-opt-term:state/oc-opt-term:logical-channel" {
    description
      "Not-supported deviation.";
    deviate not-supported;
  }

  deviation "/oc-opt-term:terminal-device/oc-opt-term:logical-channels/oc-opt-term:channel/oc-opt-term:logical-channel-assignments/oc-opt-term:assignment/oc-opt-term:state/oc-opt-term:mapping" {
    description
      "Not-supported deviation.";
    deviate not-supported;
  }

  deviation "/oc-opt-term:terminal-device/oc-opt-term:logical-channels/oc-opt-term:channel/oc-opt-term:logical-channel-assignments/oc-opt-term:assignment/oc-opt-term:state/oc-opt-term:tributary-slot-index" {
    description
      "Not-supported deviation.";
    deviate not-supported;
  }

  deviation "/oc-opt-term:terminal-device/oc-opt-term:logical-channels/oc-opt-term:channel/oc-opt-term:state/oc-opt-term:admin-state" {
    description
      "Not-supported deviation.";
    deviate not-supported;
  }

  deviation "/oc-opt-term:terminal-device/oc-opt-term:logical-channels/oc-opt-term:channel/oc-opt-term:state/oc-opt-term:client-mapping-mode" {
    description
      "Not-supported deviation.";
    deviate not-supported;
  }

  deviation "/oc-opt-term:terminal-device/oc-opt-term:logical-channels/oc-opt-term:channel/oc-opt-term:state/oc-opt-term:link-state" {
    description
      "Not-supported deviation.";
    deviate not-supported;
  }

  deviation "/oc-opt-term:terminal-device/oc-opt-term:logical-channels/oc-opt-term:channel/oc-opt-term:state/oc-opt-term:loopback-mode" {
    description
      "Not-supported deviation.";
    deviate not-supported;
  }

  deviation "/oc-opt-term:terminal-device/oc-opt-term:logical-channels/oc-opt-term:channel/oc-opt-term:state/oc-opt-term:rate-class" {
    description
      "Not-supported deviation.";
    deviate not-supported;
  }

  deviation "/oc-opt-term:terminal-device/oc-opt-term:logical-channels/oc-opt-term:channel/oc-opt-term:state/oc-opt-term:test-signal" {
    description
      "Not-supported deviation.";
    deviate not-supported;
  }
}
