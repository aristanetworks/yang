module arista-ale-counters-open-config-hardware-drop-counters {
  yang-version 1;
  namespace "http://arista.com/yang/experimental/eos/arista-ale-counters-open-config-hardware-drop-counters";
  prefix "arista-ale-counters-open-config-hardware-drop-counters";

  import openconfig-extensions { prefix "oc-ext"; }
  organization
    "Arista Networks <http://arista.com/>";
  contact
    "Arista Networks <http://arista.com/>";
  description
    "Hardware drop reason counters

    THIS YANG MODULE WAS GENERATED. DO NOT EDIT THIS FILE.";

  oc-ext:openconfig-version "1.0.0";

  revision "2023-01-01" {
    description
      "Version 1.0.0, generated on 2023-01-01";
    reference "1.0.0";
  }

  grouping hardware-drop-adverse-block-state {
    leaf ipt-crc-err-cnt {
      type uint64;
      description
        "IptCrcErrCnt counter";
    }
    leaf uc-fifo-full-drop {
      type uint64;
      description
        "UcFifoFullDrop counter";
    }
    leaf uc-fifo-sflow-drop {
      type uint64;
      description
        "UcFifoSflowDrop counter";
    }
    leaf uc-fifo-snoop-drop {
      type uint64;
      description
        "UcFifoSnoopDrop counter";
    }
    leaf uc-fifo-mirror-drop {
      type uint64;
      description
        "UcFifoMirrorDrop counter";
    }
    leaf ingr-repl-fifo-drop {
      type uint64;
      description
        "IngrReplFifoDrop counter";
    }
    leaf ingr-repl-fifo-sflow-drop {
      type uint64;
      description
        "IngrReplFifoSflowDrop counter";
    }
    leaf ingr-repl-fifo-snoop-drop {
      type uint64;
      description
        "IngrReplFifoSnoopDrop counter";
    }
    leaf ingr-repl-fifo-mirror-drop {
      type uint64;
      description
        "IngrReplFifoMirrorDrop counter";
    }
    leaf deq-delete-pkt-cnt {
      type uint64;
      description
        "DeqDeletePktCnt counter";
    }
    leaf dram-bdbs-rjct-pkt-cnt {
      type uint64;
      description
        "DramBdbsRjctPktCnt counter";
    }
    leaf dyn-rjct-pkt-cnt {
      type uint64;
      description
        "DynRjctPktCnt counter";
    }
    leaf rqp-discard-packet-ctr {
      type uint64;
      description
        "RqpDiscardPacketCtr counter";
    }
    leaf rqppc {
      type uint64;
      description
        "RqpPC counter";
    }
    leaf mcast-data-buffers-drop-ctr {
      type uint64;
      description
        "McastDataBuffersDropCtr counter";
    }
    leaf pqp-mcastpc {
      type uint64;
      description
        "PqpMcastPC counter";
    }
    leaf enq-pkt-cnt {
      type uint64;
      description
        "EnqPktCnt counter";
    }
    leaf ingress-discard-counter {
      type uint64;
      description
        "IngressDiscardCounter counter";
    }
    leaf egress-discard-counter {
      type uint64;
      description
        "EgressDiscardCounter counter";
    }
    leaf fabric-receive-cell-discard {
      type uint64;
      description
        "FabricReceiveCellDiscard counter";
    }
    leaf mesh-mc-repl-drop {
      type uint64;
      description
        "MeshMcReplDrop counter";
    }
    leaf egr-repl-mc-low-drop {
      type uint64;
      description
        "EgrReplMcLowDrop counter";
    }
    leaf egr-repl-mc-high-drop {
      type uint64;
      description
        "EgrReplMcHighDrop counter";
    }
    leaf egr-repl-uc-drop {
      type uint64;
      description
        "EgrReplUcDrop counter";
    }
    leaf reassembly-errors {
      type uint64;
      description
        "ReassemblyErrors counter";
    }
    leaf epni-aligner-error {
      type uint64;
      description
        "EpniAlignerError counter";
    }
    leaf serdes-crc-errors {
      type uint64;
      description
        "SerdesCrcErrors counter";
    }
    leaf dch-fifos-discards {
      type uint64;
      description
        "DchFifosDiscards counter";
    }
    leaf dch-reord-discards {
      type uint64;
      description
        "DchReordDiscards counter";
    }
    leaf dch-unreachables {
      type uint64;
      description
        "DchUnreachables counter";
    }
    leaf dch-fifos-multicast-low-drops {
      type uint64;
      description
        "DchFifosMulticastLowDrops counter";
    }
    leaf rtp-drh-multicast-low-drops {
      type uint64;
      description
        "RtpDrhMulticastLowDrops counter";
    }
    leaf dcm-fifos-ip-drops {
      type uint64;
      description
        "DcmFifosIpDrops counter";
    }
    leaf dcm-fifos-total-drops {
      type uint64;
      description
        "DcmFifosTotalDrops counter";
    }
    leaf dcl-fifos-total-drops {
      type uint64;
      description
        "DclFifosTotalDrops counter";
    }
    leaf drop-voq-in-forwarding-lookup-miss {
      type uint64;
      description
        "dropVoqInForwardingLookupMiss counter";
    }
    leaf drop-voq-in-no-forwarding-action {
      type uint64;
      description
        "dropVoqInNoForwardingAction counter";
    }
    description
      "Adverse attributes";
  }
  grouping hardware-drop-adverse-block {
    container state {
      uses hardware-drop-adverse-block-state;
      description
        "Adverse attributes";
    }
    description
      "Adverse block";
  }
  grouping hardware-drop-packet-processing-block-state {
    leaf drop-voq-in-port-not-vlan-member {
      type uint64;
      description
        "dropVoqInPortNotVlanMember counter";
    }
    leaf drop-voq-in-sa-equals-da {
      type uint64;
      description
        "dropVoqInSaEqualsDa counter";
    }
    leaf drop-voq-in-sa-multicast {
      type uint64;
      description
        "dropVoqInSaMulticast counter";
    }
    leaf drop-voq-in-rpf {
      type uint64;
      description
        "dropVoqInRpf counter";
    }
    leaf drop-voq-in-ip-version-error {
      type uint64;
      description
        "dropVoqInIpVersionError counter";
    }
    leaf drop-voq-in-ipv4-checksum-error {
      type uint64;
      description
        "dropVoqInIpv4ChecksumError counter";
    }
    leaf drop-voq-in-ip-ttl0 {
      type uint64;
      description
        "dropVoqInIpTtl0 counter";
    }
    leaf drop-voq-in-ipv6-unspecified-destination {
      type uint64;
      description
        "dropVoqInIpv6UnspecifiedDestination counter";
    }
    leaf drop-voq-in-ipv6-multicast-source {
      type uint64;
      description
        "dropVoqInIpv6MulticastSource counter";
    }
    leaf drop-voq-in-acl {
      type uint64;
      description
        "dropVoqInAcl counter";
    }
    leaf drop-voq-in-no-arp {
      type uint64;
      description
        "dropVoqInNoArp counter";
    }
    leaf drop-voq-in-null-route {
      type uint64;
      description
        "dropVoqInNullRoute counter";
    }
    leaf drop-voq-in-route-overflow {
      type uint64;
      description
        "dropVoqInRouteOverflow counter";
    }
    leaf drop-voq-in-pbr {
      type uint64;
      description
        "dropVoqInPbr counter";
    }
    leaf drop-voq-out-mtu-tunnel {
      type uint64;
      description
        "dropVoqOutMtuTunnel counter";
    }
    leaf drop-voq-in-ptp {
      type uint64;
      description
        "dropVoqInPtp counter";
    }
    leaf drop-voq-in-lag-discarding {
      type uint64;
      description
        "dropVoqInLagDiscarding counter";
    }
    leaf drop-voq-in-tun-vxlan {
      type uint64;
      description
        "dropVoqInTunVxlan counter";
    }
    leaf drop-voq-in-mcast-no-cpu {
      type uint64;
      description
        "dropVoqInMcastNoCpu counter";
    }
    leaf drop-voq-in-elk-error {
      type uint64;
      description
        "dropVoqInElkError counter";
    }
    leaf drop-voq-in-sa-not-found {
      type uint64;
      description
        "dropVoqInSaNotFound counter";
    }
    leaf egress-acl-drop-counter {
      type uint64;
      description
        "EgressAclDropCounter counter";
    }
    leaf drop-voq-in-mcast-empty-mcid {
      type uint64;
      description
        "dropVoqInMcastEmptyMcid counter";
    }
    leaf egr-mrouted-ttl-drop {
      type uint64;
      description
        "EgrMroutedTtlDrop counter";
    }
    leaf drop-voq-in-intf-mpls-disabled {
      type uint64;
      description
        "dropVoqInIntfMplsDisabled counter";
    }
    leaf drop-voq-in-source-port-filter {
      type uint64;
      description
        "dropVoqInSourcePortFilter counter";
    }
    leaf drop-voq-in-encap-bum-filter {
      type uint64;
      description
        "dropVoqInEncapBumFilter counter";
    }
    leaf drop-voq-in-etree-leaf {
      type uint64;
      description
        "dropVoqInEtreeLeaf counter";
    }
    leaf drop-voq-in-oam {
      type uint64;
      description
        "dropVoqInOam counter";
    }
    leaf drop-voq-in-vpls-standby-pw {
      type uint64;
      description
        "dropVoqInVplsStandbyPw counter";
    }
    leaf ingress-meter-drop {
      type uint64;
      description
        "IngressMeterDrop counter";
    }
    description
      "Packet processing attributes";
  }
  grouping hardware-drop-packet-processing-block {
    container state {
      uses hardware-drop-packet-processing-block-state;
      description
        "Packet processing attributes";
    }
    description
      "Packet processing block";
  }
  grouping hardware-drop-congestion-block-state {
    description
      "Congestion drop attributes";
  }
  grouping hardware-drop-congestion-block {
    container state {
      uses hardware-drop-congestion-block-state;
      description
        "Congestion drop attributes";
    }
    description
      "Congestion block";
  }
  grouping pipeline-arista-sand-hardware-drop-counters {
    container adverse {
      uses hardware-drop-adverse-block;
      description
        "Adverse block";
    }
    container packet-processing {
      uses hardware-drop-packet-processing-block;
      description
        "Packet processing block";
    }
    container congestion {
      uses hardware-drop-congestion-block;
      description
        "Congestion block";
    }
    description
      "Container for Sand specific hardware drop counters";
  }
  grouping pipeline-arista-hardware-drop-counters {
    container sand {
      uses pipeline-arista-sand-hardware-drop-counters;
      description
        "Container for Sand specific drop counters";
    }
    description
      "";
  }
  grouping pipeline-vendor-hardware-drop-counters {
    container arista {
      uses pipeline-arista-hardware-drop-counters;
      description
        "Container for Arista-specific drop counters";
    }
    description
      "";
  }
}
