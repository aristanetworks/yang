module arista-system-deviations {
  namespace "http://arista.com/yang/openconfig/system/deviations";
  prefix arista-system-deviations;

  import openconfig-system {
    prefix oc-sys;
  }
  import openconfig-inet-types {
    prefix oc-inet;
  }

  organization
    "Arista Networks, Inc.";
  contact
    "Arista Networks, Inc.
     Product Support";
  description
    "This module contains OpenConfig system deviations in Arista EOS.
     Copyright (c) 2017 Arista Networks, Inc. All rights reserved.";

  revision 2020-01-21 {
    description
      "Add EOS deviations for GRPC, SSH, AAA, DNS and hostname config.";
  }
  revision 2017-09-24 {
    description
      "Initial deviations file.";
    reference
      "1.0.0";
  }

  deviation "/oc-sys:system/oc-sys:dns/oc-sys:config/oc-sys:search" {
    description
      "search limited to 6 domain-names";
    deviate add {
      max-elements 6;
    }
  }

  deviation "/oc-sys:system/oc-sys:dns/oc-sys:servers/oc-sys:server" {
    description
      "name servers limited to 3";
    deviate add {
      max-elements 3;
    }
  }

  deviation "/oc-sys:system/oc-sys:dns/oc-sys:servers/oc-sys:server/oc-sys:config" {
    description
      "port of name servers must be 53";
    deviate add {
      must "port='53'" {
        error-message "port must be 53";
      }
    }
  }

  deviation "/oc-sys:system/oc-sys:dns/oc-sys:host-entries/oc-sys:host-entry/oc-sys:config/oc-sys:alias" {
    description
      "alias of host-entries is not configurable";
    deviate not-supported;
  }

  deviation "/oc-sys:system/oc-sys:memory/oc-sys:state/oc-sys:physical" {
    description
      "physical memory default value 0";
    deviate add {
      default "0";
    }
  }

  deviation "/oc-sys:system/oc-sys:aaa/oc-sys:server-groups/oc-sys:server-group/oc-sys:servers/oc-sys:server/oc-sys:config/oc-sys:address" {
    description
      "In EOS, the server address can be an IP address or hostname";
    deviate replace {
      type union {
        type oc-inet:ip-address;
        type string;
      }
    }
  }

  deviation "/oc-sys:system/oc-sys:aaa/oc-sys:server-groups/oc-sys:server-group/oc-sys:servers/oc-sys:server/oc-sys:state/oc-sys:address" {
    description
      "In EOS, the server address can be an IP address or a hostname";
    deviate replace {
      type union {
        type oc-inet:ip-address;
        type string;
      }
    }
  }

  deviation "/oc-sys:system/oc-sys:aaa/oc-sys:server-groups/oc-sys:server-group/oc-sys:servers/oc-sys:server/oc-sys:config/oc-sys:timeout" {
    description
      "In EOS, the timeout value can be between 1 and 1000";
    deviate replace {
      type uint16 {
        range "1..1000";
      }
    }
  }

  deviation "/oc-sys:system/oc-sys:aaa/oc-sys:server-groups/oc-sys:server-group/oc-sys:servers/oc-sys:server/oc-sys:radius/oc-sys:config/oc-sys:retransmit-attempts" {
    description
      "In EOS, retransmit-attempts can be between 0 and 100";
    deviate replace {
      type uint8 {
        range "0..100";
      }
    }
  }

  deviation "/oc-sys:system/oc-sys:ssh-server/oc-sys:config/oc-sys:session-limit" {
    deviate replace {
      type uint8 {
        range "0..100";
      }
    }
  }

  deviation "/oc-sys:system/oc-sys:ssh-server/oc-sys:state/oc-sys:session-limit" {
    deviate replace {
      type uint8 {
        range "0..100";
      }
    }
  }

  deviation "/oc-sys:system/oc-sys:ssh-server/oc-sys:config/oc-sys:rate-limit" {
    description
      "configuring the SSH rate-limit is not supported in EOS";
    deviate not-supported;
  }

  deviation "/oc-sys:system/oc-sys:ssh-server/oc-sys:state/oc-sys:rate-limit" {
    description
      "getting the SSH rate-limit is not supported in EOS";
    deviate not-supported;
  }

  deviation "/oc-sys:system/oc-sys:ssh-server/oc-sys:config/oc-sys:protocol-version" {
    description
      "configuring the SSH protocol-version is not supported in EOS";
    deviate not-supported;
  }

  deviation "/oc-sys:system/oc-sys:ssh-server/oc-sys:state/oc-sys:protocol-version" {
    description
      "getting the SSH protocol-version is not supported in EOS";
    deviate not-supported;
  }

  deviation "/oc-sys:system/oc-sys:grpc-server/oc-sys:config/oc-sys:port" {
    deviate replace {
      default "6030";
    }
  }

  deviation "/oc-sys:system/oc-sys:grpc-server/oc-sys:state/oc-sys:port" {
    deviate replace {
      default "6030";
    }
  }

  deviation "/oc-sys:system/oc-sys:grpc-server/oc-sys:config/oc-sys:metadata-authentication" {
    description
      "Enabling gRPC METADATA authentication is not supported";
    deviate not-supported;
  }

  deviation "/oc-sys:system/oc-sys:grpc-server/oc-sys:state/oc-sys:metadata-authentication" {
    description
      "Getting the enabled state of gRPC METADATA authentication is not supported";
    deviate not-supported;
  }

  deviation "/oc-sys:system/oc-sys:grpc-server/oc-sys:config/oc-sys:listen-addresses" {
    description
      "Configuring the IP addresses that the gRPC server should listen on is not supported";
    deviate not-supported;
  }

  deviation "/oc-sys:system/oc-sys:grpc-server/oc-sys:state/oc-sys:listen-addresses" {
    description
      "Getting the IP addresses that the gRPC server should listen on is not supported";
    deviate not-supported;
  }

  deviation "/oc-sys:system/oc-sys:ntp/oc-sys:servers/oc-sys:server/oc-sys:config/oc-sys:port" {
    description
      "The port number for NTP is not configurable in EOS.";
    deviate replace {
      config false;
    }
  }

  deviation "/oc-sys:system/oc-sys:grpc-server/oc-sys:config/oc-sys:transport-security" {
    description
      "Use gRPC transport security (e.g., TLS or SSL)";
    deviate delete {
      default "true";
    }
  }

  deviation "/oc-sys:system/oc-sys:grpc-server/oc-sys:state/oc-sys:transport-security" {
    description
      "Use gRPC transport security (e.g., TLS or SSL)";
    deviate delete {
      default "true";
    }
  }

  deviation "/oc-sys:system/oc-sys:logging/oc-sys:remote-servers/oc-sys:remote-server/oc-sys:config/oc-sys:remote-port" {
    description
      "Sets the destination port number for syslog UDP messages to the server.  The default for syslog is 514.";
    deviate not-supported;
  }

  deviation "/oc-sys:system/oc-sys:logging/oc-sys:remote-servers/oc-sys:remote-server/oc-sys:state/oc-sys:remote-port" {
    description
      "Sets the destination port number for syslog UDP messages to the server.  The default for syslog is 514.";
    deviate not-supported;
  }
}
