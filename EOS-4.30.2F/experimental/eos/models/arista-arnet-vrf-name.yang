module arista-arnet-vrf-name {
  yang-version 1;
  namespace "http://arista.com/yang/experimental/eos/arista-arnet-vrf-name";
  prefix "arista-arnet-vrf-name";

  import openconfig-extensions { prefix "oc-ext"; }
  organization
    "Arista Networks <http://arista.com/>";
  contact
    "Arista Networks <http://arista.com/>";
  description
    "Yang model for VRF Name.

    THIS YANG MODULE WAS GENERATED. DO NOT EDIT THIS FILE.";

  oc-ext:openconfig-version "0.1.0";

  revision "2022-03-28" {
    description
      "Version 0.1.0, generated on 2022-03-28";
    reference "0.1.0";
  }

  typedef vrf-name {
    type string;
    description
      "Name of a VRF.";
  }
}
