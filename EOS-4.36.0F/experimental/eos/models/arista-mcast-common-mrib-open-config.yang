module arista-mcast-common-mrib-open-config {
  yang-version 1;
  namespace "http://arista.com/yang/experimental/eos/arista-mcast-common-mrib-open-config";
  prefix "arista-mcast-common-mrib-open-config";
  
  import openconfig-extensions { prefix "oc-ext"; }
  import openconfig-inet-types { prefix "openconfig-inet-types"; }
  import openconfig-interfaces { prefix "openconfig-interfaces"; }
  import openconfig-network-instance { prefix "openconfig-network-instance"; }
  import openconfig-policy-types { prefix "openconfig-policy-types"; }
  organization
    "Arista Networks <http://arista.com/>";
  contact
    "Arista Networks <http://arista.com/>";
  description
    "Support for Static Multicast RPF Routes
    
    THIS YANG MODULE WAS GENERATED. DO NOT EDIT THIS FILE.";
  
  oc-ext:openconfig-version "1.0.0";
  
  revision "2025-05-06" {
    description
      "Version 1.0.0, generated on 2025-05-06";
    reference "1.0.0";
  }
  
  identity MRIB {
    base "openconfig-policy-types:INSTALL_PROTOCOL_TYPE";
    description
      "MRIB";
  }
  grouping routing-multicast-rib-open-config-static-mrib-key {
    leaf prefix {
      type openconfig-inet-types:ip-prefix;
      description
        "Reference to the source prefix";
    }
    description
      "Key for the Static MRIB collection";
  }
  
  grouping routing-multicast-rib-open-config-next-hop-config {
    leaf index {
      type string;
      description
        "An user-specified identifier utilised to uniquely reference the next-hop
        entry in the next-hop list. The value of this index has no semantic meaning
        other than for referencing the entry. It is observed that implementations
        typically only support a numeric value for this string.";
    }
    leaf next-hop-addr {
      type openconfig-inet-types:ip-address;
      description
        "The next-hop that is to be used for the static MRIB route - this one is
        specified as an IP address";
    }
    leaf preference {
      type uint8;
      default 1;
      description
        "Administrative Distance (preference) of the entry. The preference defines
        the order of selection when multiple sources (protocols, static, etc.)
        contribute to the same prefix entry. The lower the preference, the more
        preferable the prefix is. When this value is not specified, the preference
        is inherited from the default preference of the implementation for
        static MRIB routes.";
    }
    description
      "Configuration parameters of a next-hop entry";
  }
  
  grouping routing-multicast-rib-open-config-interface-config {
    leaf interface {
      type openconfig-interfaces:interface-id;
      description
        "Reference to a base interface. If a reference to a subinterface is
        required, this leaf must be specified to indicate the base interface.";
    }
    leaf subinterface {
      type uint32;
      description
        "Reference to a subinterface -- this requires the base interface to be
        specified using the interface leaf in this container. If only a reference to
        a base interface is required, this leaf should not be set.";
    }
    description
      "Configured reference to interface / subinterface";
  }
  
  grouping routing-multicast-rib-open-config-interface-ref {
    container config {
      uses routing-multicast-rib-open-config-interface-config;
      description
        "Configured reference to interface / subinterface";
    }
    container state {
      uses routing-multicast-rib-open-config-interface-config;
      config false;
      description
        "Operational state for interface-ref";
    }
    description
      "Reference to an interface or subinterface";
  }
  
  grouping routing-multicast-rib-open-config-next-hop-container {
    leaf index {
      type string;
      description
        "A reference to the index of the current next-hop.
        The index is intended to be a user-specified value
        which can be used to reference the next-hop in
        question, without any other semantics being
        assigned to it.";
    }
    container config {
      uses routing-multicast-rib-open-config-next-hop-config;
      description
        "Configuration parameters of a next-hop";
    }
    container state {
      uses routing-multicast-rib-open-config-next-hop-config;
      config false;
      description
        "Operational state parameters of a next-hop";
    }
    container interface-ref {
      uses routing-multicast-rib-open-config-interface-ref;
      description
        "Reference to an interface or subinterface";
    }
    description
      "A list of next-hops for the static MRIB route.";
  }
  
  grouping routing-multicast-rib-open-config-nexthops-container {
    list next-hop {
      key "index";
      uses routing-multicast-rib-open-config-next-hop-container;
      description
        "A list of next-hops for the static MRIB route.";
    }
    description
      "Configuration and state parameters for the next-hops of the
      static MRIB route.";
  }
  
  grouping routing-multicast-rib-open-config-mrib-config {
    leaf prefix {
      type openconfig-inet-types:ip-prefix;
      description
        "Source address with prefix for a static MRIB route";
    }
    description
      "Configuration data for static MRIB routes";
  }
  
  grouping routing-multicast-rib-open-config-static-mrib-container {
    uses routing-multicast-rib-open-config-static-mrib-key;
    container config {
      uses routing-multicast-rib-open-config-mrib-config;
      description
        "Configuration data for static MRIB route";
    }
    container state {
      uses routing-multicast-rib-open-config-mrib-config;
      config false;
      description
        "Operational state data for static MRIB route";
    }
    container next-hops {
      uses routing-multicast-rib-open-config-nexthops-container;
      description
        "Configuration and state parameters for the next-hops of the
        static MRIB route.";
    }
    description
      "List of locally configured static MRIB routes";
  }
  
  grouping routing-multicast-rib-open-config-mrib-routes {
    description
      "Enclosing container for the list of Static MRIB Routes";
  }
  
  augment "/openconfig-network-instance:network-instances/openconfig-network-instance:network-instance/openconfig-network-instance:protocols/openconfig-network-instance:protocol" {
    container static-mrib {
      container routes {
        list route {
          key "prefix";
          uses routing-multicast-rib-open-config-static-mrib-container;
          description
            "route list";
        }
        description
          "routes container";
      }
      description
        "static-mrib container";
    }
  }
} // main-yang
