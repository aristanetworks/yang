module arista-l1-open-config-prbs-model {
  yang-version 1;
  namespace "http://arista.com/yang/experimental/eos/arista-l1-open-config-prbs-model";
  prefix "arista-l1-open-config-prbs-model";
  
  import openconfig-extensions { prefix "oc-ext"; }
  import arista-l1-types-l1-types { prefix "arista-l1-types-l1-types"; }
  import arista-xcvr-xcvr-test-pattern { prefix "arista-xcvr-xcvr-test-pattern"; }
  import openconfig-types { prefix "openconfig-types"; }
  organization
    "Arista Networks <http://arista.com/>";
  contact
    "Arista Networks <http://arista.com/>";
  description
    "PRBS attributes
    
    THIS YANG MODULE WAS GENERATED. DO NOT EDIT THIS FILE.";
  
  oc-ext:openconfig-version "1.0.0";
  
  revision "2025-07-25" {
    description
      "Version 1.0.0, generated on 2025-07-25";
    reference "1.0.0";
  }
  
  typedef l1-open-config-prbs-test-pattern-union {
    type union {
      type arista-l1-types-l1-types:hardware-phy-test-pattern;
      type arista-xcvr-xcvr-test-pattern:xcvr-test-pattern-type;
    }
    description
      "Test pattern enum";
  }
  
  grouping l1-open-config-prbs-receive-lane-state {
    leaf bit-rate {
      type decimal64 {
        fraction-digits 2;
      }
      description
        "Current bitrate in Gbps";
    }
    leaf total-bits {
      type uint64;
      description
        "Total bits since pattern acquisition";
    }
    leaf locked {
      type arista-l1-types-l1-types:hardware-phy-test-pattern-lock;
      description
        "Signal locked";
    }
    leaf lock-lost {
      type arista-l1-types-l1-types:hardware-phy-test-pattern-lock-latch;
      description
        "Lock lost";
    }
    leaf link-state-changes {
      type uint64;
      description
        "Link lost change counter";
    }
    leaf last-link-state-change {
      type openconfig-types:timeticks64;
      description
        "Link state changed timestamp relative to Unix epoch";
    }
    leaf errors {
      type uint64;
      description
        "Bit errors total counter";
    }
    leaf last-lock-time {
      type openconfig-types:timeticks64;
      description
        "Last link lock timestamp relative to Unix epoch";
    }
    leaf errors-since-last-lock {
      type uint64;
      description
        "Bit error counters since last lock";
    }
    leaf-list transmit-capability {
      type l1-open-config-prbs-test-pattern-union;
      description
        "Supported transmit patterns";
    }
    leaf-list receive-capability {
      type l1-open-config-prbs-test-pattern-union;
      description
        "Supported receive patterns";
    }
    leaf transmit-pattern {
      type l1-open-config-prbs-test-pattern-union;
      description
        "Configured transmit test pattern";
    }
    leaf receive-pattern {
      type l1-open-config-prbs-test-pattern-union;
      description
        "Configured receive test pattern";
    }
    description
      "Receive lane state container";
  }
  
  grouping l1-open-config-prbs-uncorrected-codewords-state {
    leaf uncorrected-codewords {
      type uint64;
      description
        "number of uncorrected codewords";
    }
    description
      "Error distribution container";
  }
  
  grouping l1-open-config-prbs-error-distribution {
    container state {
      uses l1-open-config-prbs-uncorrected-codewords-state;
      description
        "Operational state data for error distribution";
    }
    description
      "Error distribution for receive lanes";
  }
  
  grouping l1-open-config-prbs-receive-lane-status {
    leaf lane {
      type uint16;
      description
        "SerDes lane number";
    }
    container state {
      uses l1-open-config-prbs-receive-lane-state;
      description
        "Operational state data for receive lanes";
    }
    container error-distribution {
      uses l1-open-config-prbs-error-distribution;
      description
        "Container for error distribution info";
    }
    description
      "Receive lane counters and error distribution";
  }
  
  grouping l1-open-config-prbs-receive-state {
    leaf-list capability {
      type l1-open-config-prbs-test-pattern-union;
      description
        "Supported patterns";
    }
    leaf pattern {
      type l1-open-config-prbs-test-pattern-union;
      description
        "Configured test pattern";
    }
    description
      "PRBS receive state";
  }
  
  grouping l1-open-config-prbs-receive-lanes-container {
    list lane {
      key "lane";
      uses l1-open-config-prbs-receive-lane-status;
      description
        "Receive attributes per SerDes lane";
    }
    description
      "Container for receive lanes";
  }
  
  grouping l1-open-config-prbs-receive-status {
    container state {
      uses l1-open-config-prbs-receive-state;
      description
        "Receive state";
    }
    container lanes {
      uses l1-open-config-prbs-receive-lanes-container;
      description
        "Receive attributes collected by SerDes lane";
    }
    description
      "Container for receive direction";
  }
  
  grouping l1-open-config-prbs-transmit-state {
    leaf-list capability {
      type l1-open-config-prbs-test-pattern-union;
      description
        "Supported patterns";
    }
    leaf pattern {
      type l1-open-config-prbs-test-pattern-union;
      description
        "Test pattern currently transmitted";
    }
    description
      "PRBS transmit state";
  }
  
  grouping l1-open-config-prbs-transmit-status {
    container state {
      uses l1-open-config-prbs-transmit-state;
      description
        "Transmit state";
    }
    description
      "Container for transmit direction";
  }
  
} // main-yang
