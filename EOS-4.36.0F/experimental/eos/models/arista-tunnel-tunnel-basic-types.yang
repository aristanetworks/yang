module arista-tunnel-tunnel-basic-types {
  yang-version 1;
  namespace "http://arista.com/yang/experimental/eos/arista-tunnel-tunnel-basic-types";
  prefix "arista-tunnel-tunnel-basic-types";
  
  import openconfig-extensions { prefix "oc-ext"; }
  organization
    "Arista Networks <http://arista.com/>";
  contact
    "Arista Networks <http://arista.com/>";
  description
    "Tunnel related types
    
    THIS YANG MODULE WAS GENERATED. DO NOT EDIT THIS FILE.";
  
  oc-ext:openconfig-version "1.0.0";
  
  revision "2021-10-20" {
    description
      "Version 1.0.0, generated on 2021-10-20";
    reference "1.0.0";
  }
  
  typedef tunnel-tunnel-table-tunnel-id {
    type uint64 {
      range "0..1125899906842623";
    }
    default 0;
    description
      "Opaque identifier for a tunnel";
  }
  
  typedef tunnel-tunnel-table-encap-type {
    type enumeration {
      enum INVALID_ENCAP {
        value 0;
        description
          "";
      }
      enum GRE_ENCAP {
        value 1;
        description
          "";
      }
      enum IP_SEC_ENCAP {
        value 2;
        description
          "";
      }
      enum IP_SEC_GRE_ENCAP {
        value 3;
        description
          "";
      }
      enum MPLS_ENCAP {
        value 4;
        description
          "";
      }
      enum VXLAN_ENCAP {
        value 5;
        description
          "";
      }
      enum IP_IN_IP_ENCAP {
        value 6;
        description
          "";
      }
      enum SRV6_TUNNEL_ENCAP {
        value 7;
        description
          "";
      }
      enum DSF_ENCAP {
        value 8;
        description
          "";
      }
      enum GUE_ENCAP {
        value 9;
        description
          "";
      }
      enum COMBINED_ENCAP {
        value 10;
        description
          "";
      }
    }
    description
      "Encap types";
  }
  
  typedef tunnel-tunnel-table-tunnel-type {
    type enumeration {
      enum INVALID_TUNNEL {
        value 0;
        description
          "";
      }
      enum BGP_LU_FORWARDING_TUNNEL {
        value 1;
        description
          "";
      }
      enum BGP_LU_TUNNEL {
        value 2;
        description
          "";
      }
      enum LDP_TUNNEL {
        value 3;
        description
          "";
      }
      enum NEXTHOP_TUNNEL {
        value 4;
        description
          "";
      }
      enum STATIC_TUNNEL {
        value 5;
        description
          "";
      }
      enum EVPN_VXLAN_TUNNEL {
        value 6;
        description
          "";
      }
      enum SR_TUNNEL {
        value 7;
        description
          "";
      }
      enum SR_TE_SEGMENT_LIST_TUNNEL {
        value 8;
        description
          "";
      }
      enum STATIC_INTERFACE_TUNNEL {
        value 9;
        description
          "";
      }
      enum RSVP_TUNNEL {
        value 10;
        description
          "";
      }
      enum NEXTHOP_GROUP_TUNNEL {
        value 11;
        description
          "";
      }
      enum TI_LFA_TUNNEL {
        value 12;
        description
          "";
      }
      enum OSPF_SR_TUNNEL {
        value 13;
        description
          "";
      }
      enum SR_TE_POLICY_TUNNEL {
        value 14;
        description
          "";
      }
      enum VXLAN_VTEP_ENCAP_TUNNEL {
        value 15;
        description
          "";
      }
      enum RSVP_LER_TUNNEL {
        value 16;
        description
          "";
      }
      enum RSVP_FRR_TUNNEL {
        value 17;
        description
          "";
      }
      enum EOS_SDK_SBFD_SESSION_TUNNEL {
        value 18;
        description
          "";
      }
      enum VXLAN_TUNNEL {
        value 19;
        description
          "";
      }
      enum RSVP_LER_SUB_TUNNEL {
        value 20;
        description
          "";
      }
      enum ISIS_FLEX_ALGO_TUNNEL {
        value 21;
        description
          "";
      }
      enum MLDP_P_2_MP_TUNNEL {
        value 22;
        description
          "";
      }
      enum STATIC_MCAST_TUNNEL {
        value 23;
        description
          "";
      }
      enum IP_IN_IP_TUNNEL {
        value 24;
        description
          "";
      }
      enum SRV6_TRANSPORT_TUNNEL {
        value 25;
        description
          "";
      }
      enum VOQ_FABRIC_TUNNEL {
        value 26;
        description
          "";
      }
      enum GUE_TUNNEL {
        value 27;
        description
          "";
      }
      enum RSVP_P_2_MP_TUNNEL {
        value 28;
        description
          "";
      }
      enum SRV6_SR_TE_SEGMENT_LIST_TUNNEL {
        value 29;
        description
          "";
      }
      enum ISIS_REMOTE_TI_LFA_TUNNEL {
        value 30;
        description
          "";
      }
      enum ISIS_SRV6_IGP_TUNNEL {
        value 31;
        description
          "";
      }
      enum ISIS_SRV6_IGP_TILFA_TUNNEL {
        value 32;
        description
          "";
      }
      enum MAX_TUNNEL_TYPE {
        value 33;
        description
          "";
      }
    }
    description
      "Tunnel types";
  }
  
} // main-yang
