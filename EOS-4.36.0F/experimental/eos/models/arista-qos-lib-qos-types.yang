module arista-qos-lib-qos-types {
  yang-version 1;
  namespace "http://arista.com/yang/experimental/eos/arista-qos-lib-qos-types";
  prefix "arista-qos-lib-qos-types";
  
  import openconfig-extensions { prefix "oc-ext"; }
  organization
    "Arista Networks <http://arista.com/>";
  contact
    "Arista Networks <http://arista.com/>";
  description
    "Yang models for Qos Policy Map Counters
    
    THIS YANG MODULE WAS GENERATED. DO NOT EDIT THIS FILE.";
  
  oc-ext:openconfig-version "1.0.0";
  
  revision "2025-08-11" {
    description
      "Version 1.0.0, generated on 2025-08-11";
    reference "1.0.0";
  }
  
  grouping qos-policer-counter {
    leaf intf-name {
      type string;
      description
        "interface name";
    }
    leaf red-pkts {
      type uint64;
      description
        "red packets";
    }
    leaf red-bytes {
      type uint64;
      description
        "red bytes";
    }
    leaf yellow-pkts {
      type uint64;
      description
        "yellow packets";
    }
    leaf yellow-bytes {
      type uint64;
      description
        "yellow bytes";
    }
    leaf green-pkts {
      type uint64;
      description
        "green packets";
    }
    leaf green-bytes {
      type uint64;
      description
        "green bytes";
    }
    description
      "
      interface policer counter
        ";
    }
    
  } // main-yang
