module arista-ale-counters-open-config-control-plane-traffic-counters-augment {
  yang-version 1;
  namespace "http://arista.com/yang/experimental/eos/arista-ale-counters-open-config-control-plane-traffic-counters-augment";
  prefix "arista-ale-counters-open-config-control-plane-traffic-counters-augment";
  
  import openconfig-extensions { prefix "oc-ext"; }
  organization
    "Arista Networks <http://arista.com/>";
  contact
    "Arista Networks <http://arista.com/>";
  description
    "Vendor-specific control-plane traffic counters
    
    THIS YANG MODULE WAS GENERATED. DO NOT EDIT THIS FILE.";
  
  oc-ext:openconfig-version "1.0.0";
  
  revision "2023-02-02" {
    description
      "Version 1.0.0, generated on 2023-02-02";
    reference "1.0.0";
  }
  
  grouping ale-counters-open-config-control-plane-traffic-counters {
    leaf queued {
      type uint64;
      description
        "This counter counts the number of packets enqueued.";
    }
    leaf queued-bytes {
      type uint64;
      description
        "This counter counts the number of bytes enqueued.";
    }
    leaf dropped {
      type uint64;
      description
        "This counter counts the number of packets dropped.";
    }
    leaf dropped-bytes {
      type uint64;
      description
        "This counter counts the number of bytes dropped.";
    }
    description
      "Container for Sand specific control-plane traffic counters.";
  }
  
  grouping ale-counters-open-config-control-plane-traffic-counters-state {
    description
      "Container for Sand specific control-plane traffic counters.";
  }
  
  grouping ale-counters-open-config-control-plane-traffic-counters-state-strata {
    container acl-log {
      uses ale-counters-open-config-control-plane-traffic-counters;
      description
        "Control-plane traffic for ACL entries that deny traffic with logging.";
    }
    container arp {
      uses ale-counters-open-config-control-plane-traffic-counters;
      description
        "Control-plane traffic for ARP protocol packets.";
    }
    container bfd {
      uses ale-counters-open-config-control-plane-traffic-counters;
      description
        "Control-plane traffic for L2 control BFD and Micro BFD packets.";
    }
    container bgp {
      uses ale-counters-open-config-control-plane-traffic-counters;
      description
        "Control-plane traffic for BGP.";
    }
    container bpdu {
      uses ale-counters-open-config-control-plane-traffic-counters;
      description
        "Control-plane traffic for L2 control BPDU (STP) packets.";
    }
    container cfm {
      uses ale-counters-open-config-control-plane-traffic-counters;
      description
        "Control-plane traffic for CFM.";
    }
    container cvx {
      uses ale-counters-open-config-control-plane-traffic-counters;
      description
        "Control-plane traffic for CVX.";
    }
    container cvx-heartbeat {
      uses ale-counters-open-config-control-plane-traffic-counters;
      description
        "Control-plane traffic for CVX keep alives.";
    }
    container dot1x-eapol {
      uses ale-counters-open-config-control-plane-traffic-counters;
      description
        "Control-plane traffic for Dot1xEapol if Dot1xMBA Is enabled, otherwise Dot1xEapol will use the LLDP queue.";
    }
    container dot1x-mba {
      uses ale-counters-open-config-control-plane-traffic-counters;
      description
        "Control-plane traffic for 802.1X MBA.";
    }
    container glean {
      uses ale-counters-open-config-control-plane-traffic-counters;
      description
        "Control-plane traffic for IP packets needing ARP resolution.";
    }
    container igmp {
      uses ale-counters-open-config-control-plane-traffic-counters;
      description
        "Control-plane traffic for IGMP/MLD snooping packets.";
    }
    container ip-locking {
      uses ale-counters-open-config-control-plane-traffic-counters;
      description
        "Control-plane traffic for IP locking.";
    }
    container l3-dest-miss {
      uses ale-counters-open-config-control-plane-traffic-counters;
      description
        "Control-plane traffic for Routing table lookup fails.";
    }
    container l3-slow-path {
      uses ale-counters-open-config-control-plane-traffic-counters;
      description
        "Counts Layer 3 traffic punted to the CPU for slow-path processing that is not handled by a more specific CoPP queue. This typically includes non-critical traffic.";
    }
    container lacp {
      uses ale-counters-open-config-control-plane-traffic-counters;
      description
        "Control-plane traffic for LACP.";
    }
    container lldp {
      uses ale-counters-open-config-control-plane-traffic-counters;
      description
        "Control-plane traffic for L2 control LLDP packets and Dot1xEapol packets if Dot1xMba is enabled.";
    }
    container mlag {
      uses ale-counters-open-config-control-plane-traffic-counters;
      description
        "Control-plane traffic for MLAG.";
    }
    container mod {
      uses ale-counters-open-config-control-plane-traffic-counters;
      description
        "Control-plane traffic that the Mirror on demand feature will send dropped packets to.";
    }
    container multicast-ll {
      uses ale-counters-open-config-control-plane-traffic-counters;
      description
        "Control-plane traffic for Link Local multicast packets.";
    }
    container multicast-miss {
      uses ale-counters-open-config-control-plane-traffic-counters;
      description
        "Control-plane traffic for L3 lookup fails, used for learning.";
    }
    container nat {
      uses ale-counters-open-config-control-plane-traffic-counters;
      description
        "Control-plane traffic for packets that match the dynamic NAT related config.";
    }
    container ospf-isis {
      uses ale-counters-open-config-control-plane-traffic-counters;
      description
        "Control-plane traffic for OSPF or ISIS packets.";
    }
    container pim {
      uses ale-counters-open-config-control-plane-traffic-counters;
      description
        "Control-plane traffic for PIM.";
    }
    container ptp {
      uses ale-counters-open-config-control-plane-traffic-counters;
      description
        "Control-plane traffic for L2 PTP packets.";
    }
    container self-ip {
      uses ale-counters-open-config-control-plane-traffic-counters;
      description
        "Control-plane traffic for packets whose destination IP address matches the switch.";
    }
    container self-ip-tc6-tc7 {
      uses ale-counters-open-config-control-plane-traffic-counters;
      description
        "Control-plane traffic for packets whose destination IP address matches the switch with a traffic class of 6 or 7.";
    }
    container sflow {
      uses ale-counters-open-config-control-plane-traffic-counters;
      description
        "Control-plane traffic for Sflow packets being sampled At source/destination towards the CPU.";
    }
    container switched-tc3-tc5 {
      uses ale-counters-open-config-control-plane-traffic-counters;
      description
        "Control-plane traffic for L2 packets with a traffic class between 3 to 5.";
    }
    container switched-tc6-tc7 {
      uses ale-counters-open-config-control-plane-traffic-counters;
      description
        "Control-plane traffic for L2 packets with a traffic class between 6 to 7.";
    }
    container ttl1 {
      uses ale-counters-open-config-control-plane-traffic-counters;
      description
        "Control-plane traffic for L2 final hops.";
    }
    container vrrp {
      uses ale-counters-open-config-control-plane-traffic-counters;
      description
        "Control-plane traffic for VRRP L3 control packets.";
    }
    container vxlan-encap {
      uses ale-counters-open-config-control-plane-traffic-counters;
      description
        "Control-plane traffic for VARP VTEP encapsulation.";
    }
    container vxlan-vtep-learn {
      uses ale-counters-open-config-control-plane-traffic-counters;
      description
        "Control-plane traffic for learning the MAC from a remote VTEP.";
    }
    container other {
      uses ale-counters-open-config-control-plane-traffic-counters;
      description
        "Control-plane traffic for packets sent to the CPU that are not filtered against any of the other queues defined by an endpoint.";
    }
    description
      "Container for Strata specific control-plane traffic counters.";
  }
  
  grouping ale-counters-open-config-pipeline-arista-sand-control-plane-traffic-counters {
    description
      "Container for Sand specific control-plane traffic counters.";
  }
  
  grouping ale-counters-open-config-pipeline-arista-strata-control-plane-traffic-counters {
    container state {
      uses ale-counters-open-config-control-plane-traffic-counters-state-strata;
      description
        "";
    }
    description
      "Container for Strata specific control-plane traffic counters.";
  }
  
  grouping ale-counters-open-config-pipeline-arista-control-plane-traffic-counters {
    container strata {
      uses ale-counters-open-config-pipeline-arista-strata-control-plane-traffic-counters;
      description
        "Container for Strata specific control-plane traffic counters.";
    }
    description
      "";
  }
  
  grouping ale-counters-open-config-pipeline-vendor-control-plane-traffic-counters {
    description
      "";
  }
  
} // augmented-yang
