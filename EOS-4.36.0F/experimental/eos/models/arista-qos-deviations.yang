module arista-qos-deviations {
  namespace "http://arista.com/yang/openconfig/qos/deviations";
  prefix arista-qos-deviations;

  import openconfig-qos {
    prefix oc-qos;
  }

  import openconfig-extensions {
    prefix oc-ext;
  }

  organization
    "Arista Networks, Inc.";
  contact
    "Arista Networks, Inc.
     Product Support";
  description
    "This module contains OpenConfig QoS augments in Arista EOS.

     Copyright (c) 2024 Arista Networks, Inc. All rights reserved.";
  oc-ext:openconfig-version "1.0.2";

  revision 2026-01-14 {
    description
     "Update valid range for set-dscp node in classifiers";
    reference
      "1.0.2";
  }

  revision 2025-12-11 {
    description
     "Update valid value of use-shared-buffer in bufferAllocationProfile";
    reference
      "1.0.2";
  }

  revision 2025-12-18 {
    description
     "Restrict exceed-action drop to TRUE for the one-rate two-color scheduler policy";
    reference
      "1.0.2";
  }

  revision 2025-11-19 {
    description
     "Update valid range for staticSharedBufferLimitTemporal in bufferAllocationProfile";
    reference
      "1.0.1";
  }

  revision 2024-02-28 {
    description
      "Initial deviation file.";
    reference
      "1.0.0";
  }

  deviation "/oc-qos:qos/oc-qos:classifiers/oc-qos:classifier/oc-qos:terms/oc-qos:term/oc-qos:actions/oc-qos:remark/oc-qos:config/oc-qos:set-dscp" {
    description
      "classifier dscp range is restricted in EOS";
    deviate replace {
      type uint8 {
        range "0..63";
      }
    }
  }

  deviation "/oc-qos:qos/oc-qos:buffer-allocation-profiles/oc-qos:buffer-allocation-profile/oc-qos:queues/oc-qos:queue/oc-qos:config/oc-qos:use-shared-buffer" {
    description
      "buffer allocation profile use-shared-buffer can only support TRUE";
    deviate add {
      must ". = 'true'" {
        error-message "use-shared-buffer can only be set to TRUE";
      }
    }
  }

  deviation "/oc-qos:qos/oc-qos:buffer-allocation-profiles/oc-qos:buffer-allocation-profile/oc-qos:queues/oc-qos:queue/oc-qos:config/oc-qos:static-shared-buffer-limit-temporal" {
    description
      "buffer allocation profile static-shared-buffer-limit-temporal range is restricted in EOS";
    deviate replace {
      type uint32 {
        range "0..1000000";
      }
    }
  }

  deviation "/oc-qos:qos/oc-qos:queue-management-profiles/oc-qos:queue-management-profile/oc-qos:wred/oc-qos:uniform/oc-qos:config/oc-qos:weight" {
    description
      "queue management profile wred weight range is restricted in EOS";
    deviate replace {
      type uint32 {
        range "0..15";
      }
    }
  }

  deviation "/oc-qos:qos/oc-qos:queue-management-profiles/oc-qos:queue-management-profile/oc-qos:wred/oc-qos:uniform/oc-qos:state/oc-qos:weight" {
    description
      "queue management profile wred weight range is restricted in EOS";
    deviate replace {
      type uint32 {
        range "0..15";
      }
    }
  }

  deviation "/oc-qos:qos/oc-qos:queue-management-profiles/oc-qos:queue-management-profile/oc-qos:wred/oc-qos:uniform/oc-qos:config/oc-qos:min-threshold" {
    description
      "queue management profile wred min-threshold range is restricted in EOS";
    deviate replace {
      type uint32 {
        range "0..4294967294";
      }
    }
  }

  deviation "/oc-qos:qos/oc-qos:queue-management-profiles/oc-qos:queue-management-profile/oc-qos:wred/oc-qos:uniform/oc-qos:config/oc-qos:max-threshold" {
    description
      "queue management profile wred max-threshold range is restricted in EOS";
    deviate replace {
      type uint32 {
        range "0..4294967294";
      }
    }
  }

  deviation "/oc-qos:qos/oc-qos:queue-management-profiles/oc-qos:queue-management-profile/oc-qos:wred/oc-qos:uniform/oc-qos:state/oc-qos:min-threshold" {
    description
      "queue management profile wred min-threshold range is restricted in EOS";
    deviate replace {
      type uint32 {
        range "0..4294967294";
      }
    }
  }

  deviation "/oc-qos:qos/oc-qos:queue-management-profiles/oc-qos:queue-management-profile/oc-qos:wred/oc-qos:uniform/oc-qos:state/oc-qos:max-threshold" {
    description
      "queue management profile wred max-threshold range is restricted in EOS";
    deviate replace {
      type uint32 {
        range "0..4294967294";
      }
    }
  }

  deviation "/oc-qos:qos/oc-qos:queue-management-profiles/oc-qos:queue-management-profile/oc-qos:wred/oc-qos:uniform/oc-qos:config/oc-qos:max-drop-probability-percent" {
    description
      "queue management profile max-drop-probability-percent range is restricted in EOS";
    deviate replace {
      type uint8 {
        range "1..100";
      }
    }
  }

  deviation "/oc-qos:qos/oc-qos:queue-management-profiles/oc-qos:queue-management-profile/oc-qos:wred/oc-qos:uniform/oc-qos:state/oc-qos:max-drop-probability-percent" {
    description
      "queue management profile max-drop-probability-percent range is restricted in EOS";
    deviate replace {
      type uint8 {
        range "1..100";
      }
    }
  }

  deviation "/oc-qos:qos/oc-qos:classifiers/oc-qos:classifier/oc-qos:terms/oc-qos:term/oc-qos:conditions/oc-qos:ipv4/oc-qos:config/oc-qos:dscp" {
    description
      "classifier dscp range is restricted in EOS";
    deviate replace {
      type uint8 {
        range "0..63";
      }
    }
  }

  deviation "/oc-qos:qos/oc-qos:classifiers/oc-qos:classifier/oc-qos:terms/oc-qos:term/oc-qos:conditions/oc-qos:ipv6/oc-qos:config/oc-qos:dscp" {
    description
      "classifier dscp range is restricted in EOS";
    deviate replace {
      type uint8 {
        range "0..63";
      }
    }
  }

  deviation "/oc-qos:qos/oc-qos:classifiers/oc-qos:classifier/oc-qos:terms/oc-qos:term/oc-qos:conditions/oc-qos:ipv4/oc-qos:state/oc-qos:dscp" {
    description
      "classifier dscp range is restricted in EOS";
    deviate replace {
      type uint8 {
        range "0..63";
      }
    }
  }

  deviation "/oc-qos:qos/oc-qos:classifiers/oc-qos:classifier/oc-qos:terms/oc-qos:term/oc-qos:conditions/oc-qos:ipv6/oc-qos:state/oc-qos:dscp" {
    description
      "classifier dscp range is restricted in EOS";
    deviate replace {
      type uint8 {
        range "0..63";
      }
    }
  }
  
  deviation "/oc-qos:qos/oc-qos:scheduler-policies/oc-qos:scheduler-policy/oc-qos:schedulers/oc-qos:scheduler/oc-qos:one-rate-two-color/oc-qos:exceed-action/oc-qos:config/oc-qos:drop" {
    description
      "In the one-rate two-color scheduler policy, the exceed action parameter drop is restricted to TRUE";
    deviate add {
      must ". = 'true'" {
        error-message "exceed action drop must be set to TRUE.";
      }
    }
  }
}
