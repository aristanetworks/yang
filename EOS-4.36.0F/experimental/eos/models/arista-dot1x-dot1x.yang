module arista-dot1x-dot1x {
  yang-version 1;
  namespace "http://arista.com/yang/experimental/eos/arista-dot1x-dot1x";
  prefix "arista-dot1x-dot1x";
  
  import openconfig-extensions { prefix "oc-ext"; }
  organization
    "Arista Networks <http://arista.com/>";
  contact
    "Arista Networks <http://arista.com/>";
  description
    "Enum definitions for Dot1x augmentations model
    
    THIS YANG MODULE WAS GENERATED. DO NOT EDIT THIS FILE.";
  
  oc-ext:openconfig-version "1.0.0";
  
  revision "2025-08-26" {
    description
      "Version 1.0.0, generated on 2025-08-26";
    reference "1.0.0";
  }
  
  typedef dot1x-reauth-behavior {
    type enumeration {
      enum DO_NOT_REAUTH {
        value 0;
        description
          "Do not reauthenticate the authenticated session";
      }
      enum REAUTH {
        value 1;
        description
          "Reauthenticate the authenticated session";
      }
      enum DROP_THEN_REAUTH {
        value 2;
        description
          "Clear existing authenticated session before starting reauthentication";
      }
      enum QUIET_REAUTH {
        value 3;
        description
          "Reauthenticate after quiet period for fallback VLAN scenarios";
      }
    }
    description
      "Reauthentication Behavior";
  }
  
  typedef dot1x-host-mode {
    type enumeration {
      enum SINGLE_HOST {
        value 0;
        description
          "SINGLE_HOST";
      }
      enum MULTI_HOST {
        value 1;
        description
          "MULTI_HOST";
      }
      enum MULTI_DOMAIN {
        value 2;
        description
          "AUTH_ALL_HOST";
      }
    }
    description
      "dot1x-host-mode";
  }
  
  typedef dot1x-port-ctrl-setting {
    type enumeration {
      enum CONTROLLED {
        value 0;
        description
          "Enable 802.1X for the interface";
      }
      enum FORCE_AUTH {
        value 1;
        description
          "Disable 802.1X and put the interface into authorized state";
      }
      enum FORCE_UNAUTH {
        value 2;
        description
          "Disable 802.1X and put the interface into unauthorized state";
      }
    }
    description
      "802.1X port control state of the interface";
  }
  
  typedef dot1x-port-auth-state {
    type enumeration {
      enum BLOCKED {
        value 0;
        description
          "Port is unauthorized";
      }
      enum AUTHORIZED {
        value 1;
        description
          "Port is authorized";
      }
      enum GUEST_VLAN {
        value 2;
        description
          "Port is authorized through guest VLAN";
      }
      enum RESTRICTED_VLAN {
        value 3;
        description
          "Port is authorized through restricted VLAN";
      }
    }
    description
      "Authorization state of the interface";
  }
  
  typedef dot1x-auth-method {
    type enumeration {
      enum EAPOL {
        value 0;
        description
          "EAPoL";
      }
      enum MAC_BASED_AUTH {
        value 1;
        description
          "MAC-based authentication";
      }
      enum EAPOL_FALLBACK_MBA {
        value 2;
        description
          "MAC-based Authentication fallback for EAPoL authentication failure";
      }
      enum AUTH_PHONE {
        value 3;
        description
          "Forcefully authorized phone device";
      }
    }
    description
      "Method used to authenticate the session";
  }
  
  typedef dot1x-framed-ip-source {
    type enumeration {
      enum SOURCE_NONE {
        value 0;
        description
          "No framed IP address has been obtained from any source";
      }
      enum SOURCE_AAA_ACCEPT {
        value 1;
        description
          "Framed IP address obtained from AAA";
      }
      enum SOURCE_L_3_NBR_BY_GNMI {
        value 2;
        description
          "Framed IP address obtained from L3 neighbor";
      }
      enum SOURCE_IP_LOCKING {
        value 3;
        description
          "Framed IP address obtained from IP Locking";
      }
      enum SOURCE_ARP {
        value 4;
        description
          "Framed IP address obtained from ARP";
      }
      enum SOURCE_LLDP {
        value 5;
        description
          "Framed IP address obtained from LLDP";
      }
    }
    description
      "Source of Framed IP address";
  }
  
  typedef dot1x-session-replace-detection {
    type enumeration {
      enum DETECTION_DISABLED {
        value 0;
        description
          "No action is taken when frequent session replacements are detected";
      }
      enum LOG_ONLY {
        value 1;
        description
          "Generate a log entry when frequent session replacements are detected";
      }
      enum ERRDISABLE {
        value 2;
        description
          "Disable port when frequent session replacements are detected";
      }
    }
    description
      "Action to take when frequent session replacements are detected";
  }
  
  typedef dot1x-device-type {
    type enumeration {
      enum UNCLASSIFIED {
        value 0;
        description
          "Default classification when no device type is identified";
      }
      enum PHONE {
        value 1;
        description
          "Represents a device classified as a phone";
      }
      enum NO_TYPE {
        value 2;
        description
          "Explicit indication that the device has no assigned type";
      }
    }
    description
      "Indicates the device type classification associated with the authenticated session";
  }
  
  typedef dot1x-mvrp-state {
    type enumeration {
      enum INVALID {
        value 0;
        description
          "Invaid MVRP config received from AAA";
      }
      enum NOT_RECEIVED {
        value 1;
        description
          "MVRP config not received from AAA";
      }
      enum DISABLE {
        value 2;
        description
          "MVRP is disabled on the interface";
      }
      enum ENABLE {
        value 3;
        description
          "MVRP is enabled on the interface";
      }
    }
    description
      "Indicates the operational state of MVRP on the interface";
  }
  
} // main-yang
