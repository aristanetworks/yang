module arista-dcb-pfc {
  yang-version 1;
  namespace "http://arista.com/yang/experimental/eos/arista-dcb-pfc";
  prefix "arista-dcb-pfc";
  
  import openconfig-extensions { prefix "oc-ext"; }
  import arista-exp-eos { prefix "arista-exp-eos"; }
  organization
    "Arista Networks <http://arista.com/>";
  contact
    "Arista Networks <http://arista.com/>";
  description
    "This module contains Arista-specificPriority Flow Control (PFC) data.
    
    THIS YANG MODULE WAS GENERATED. DO NOT EDIT THIS FILE.";
  
  oc-ext:openconfig-version "1.0.0";
  
  revision "2025-05-28" {
    description
      "Version 1.0.0, generated on 2025-05-28";
    reference "1.0.0";
  }
  
  typedef pfc-percent-allowed-zero {
    type uint8 {
      range "0..101";
    }
    default 101;
    description
      "Percentage";
  }
  
  typedef pfc-fadt-alpha {
    type int8 {
      range "-15..15";
    }
    default 0;
    description
      "FADT alpha parameter (burst-absorption-factor)";
  }
  
  typedef pfc-oc-percent-allowed-zero {
    type union {
      type pfc-percent-allowed-zero;
      type boolean;
    }
    description
      "Percentage, with invalid state";
  }
  
  typedef pfc-profile-state {
    type enumeration {
      enum PENDING {
        value 0;
        description
          "Profile has uncommitted changes (is being configured)";
      }
      enum ACTIVE {
        value 1;
        description
          "Profile is valid and may be assigned to PGs";
      }
      enum MODIFIED {
        value 2;
        description
          "Profile is a modified default that is valid and may be assigned to PGs";
      }
      enum INVALID {
        value 3;
        description
          "Profile has invalid configuration set and may not be assigned to PGs";
      }
      enum OUT_OF_RESOURCES {
        value 6;
        description
          "Switch is out of profile IDs and cannot assign this additional profile";
      }
    }
    description
      "Profile state after profile validation";
  }
  
  grouping pfc-fadt-params {
    leaf min {
      type uint64;
      description
        "Minimum parameter";
    }
    leaf max {
      type uint64;
      description
        "Maximum parameter";
    }
    leaf alpha {
      type pfc-fadt-alpha;
      description
        "FADT alpha parameter (burst-absorption-factor)";
    }
    description
      "FADT parameters";
  }
  
  grouping pfc-fadt-profile-params {
    leaf resume-offset {
      type uint64;
      description
        "Offset from PFC pause threshold to unpause";
    }
    leaf headroom {
      type uint64;
      description
        "Reserved amount to buffer packets in-flight after PFC";
    }
    leaf pause-alpha {
      type pfc-fadt-alpha;
      description
        "FADT alpha parameter for dynamic threshold";
    }
    leaf pause-max {
      type uint64;
      description
        "FADT maximum to PFC pause";
    }
    leaf pause-min {
      type uint64;
      description
        "FADT minimum to PFC pause";
    }
    leaf reject-alpha {
      type pfc-fadt-alpha;
      description
        "FADT alpha before ingress/priority queue drops";
    }
    leaf reject-max {
      type uint64;
      description
        "FADT maximum before ingress/priority queue drops";
    }
    leaf reject-min {
      type uint64;
      description
        "FADT minimum before ingress/priority queue drops";
    }
    description
      "FADT profile parameters";
  }
  
  grouping pfc-fadt-profile-params-byte-oc-wrapper {
    container state {
      uses pfc-fadt-profile-params;
      description
        "FADT profile parameters for buffers in bytes";
    }
    description
      "FADT profile parameters";
  }
  
  grouping pfc-fadt-profile {
    leaf name {
      type string;
      description
        "Profile name";
    }
    container bytes {
      uses pfc-fadt-profile-params-byte-oc-wrapper;
      description
        "FADT profile parameters for buffers in bytes";
    }
    description
      "FADT profile with packet-buffer configuration";
  }
  
  grouping pfc-fadt-status-oc-wrapper {
    leaf status {
      type pfc-profile-state;
      description
        "Profile state after profile validation";
    }
    description
      "Profile state after profile validation";
  }
  
  grouping pfc-fadt-profile-status {
    container state {
      uses pfc-fadt-status-oc-wrapper;
      description
        "Profile state after profile validation";
    }
    uses pfc-fadt-profile;
    description
      "FADT profile status";
  }
  
  grouping pfc-pool-allocation-percent {
    description
      "Pool allocation percentage";
  }
  
  grouping pfc-packet-buffer-profile-status {
    container pool-allocation-percent {
      uses pfc-pool-allocation-percent;
      description
        "Global resource allocation percentages";
    }
    description
      "A mapping of priority-flow-control packet-buffer profile name to profile model";
  }
  
  grouping pfc-config {
    leaf-list lossless-priorities {
      type uint8;
      description
        "Priorities assigned to lossless profiles";
    }
    description
      "Priority-flow-control configuration state";
  }
  
  augment "/arista-exp-eos:arista" {
    container pfc {
      container profiles {
        list profile {
          key "name";
          config false;
          uses pfc-fadt-profile-status;
          description
            "profile list";
        }
        description
          "profiles container";
      }
      container state {
        config false;
        leaf headroom-pct {
          type pfc-oc-percent-allowed-zero;
          config false;
          description
            "Percent of global resources allocated to headroom pool";
        }
        uses pfc-config;
        description
          "state container";
      }
      description
        "pfc container";
    }
  }
} // main-yang
