module arista-l1-open-config-optical-channel-model-augment {
  yang-version 1;
  namespace "http://arista.com/yang/experimental/eos/arista-l1-open-config-optical-channel-model-augment";
  prefix "arista-l1-open-config-optical-channel-model-augment";
  
  import openconfig-extensions { prefix "oc-ext"; }
  import arista-l1-open-config-xcvr-oc-types { prefix "arista-l1-open-config-xcvr-oc-types"; }
  import openconfig-platform { prefix "openconfig-platform"; }
  import openconfig-transport-types { prefix "openconfig-transport-types"; }
  import openconfig-terminal-device { prefix "openconfig-terminal-device"; }
  organization
    "Arista Networks <http://arista.com/>";
  contact
    "Arista Networks <http://arista.com/>";
  description
    "Attributes related to optical parameters
    
    THIS YANG MODULE WAS GENERATED. DO NOT EDIT THIS FILE.";
  
  oc-ext:openconfig-version "1.0.0";
  
  revision "2022-05-12" {
    description
      "Version 1.0.0, generated on 2022-05-12";
    reference "1.0.0";
  }
  
  grouping l1-open-config-xcvr-optical-channel-state {
    container q-margin {
      uses arista-l1-open-config-xcvr-oc-types:l1-open-config-xcvr-avg-min-max-instant-stats;
      description
        "qMargin";
    }
    description
      "Container for the state of the optical channel";
  }
  
  grouping l1-open-config-xcvr-optical-channel {
    description
      "Container for the optical channel attributes";
  }
  
  grouping l1-open-config-xcvr-optical-channel-config {
    description
      "Container for the config of the optical channel";
  }
  
  grouping l1-open-config-xcvr-optical-channel-config-base {
    description
      "Config container for the optical channel attributes";
  }
  
  grouping l1-open-config-xcvr-logical-channel-index {
    description
      "Index for a physical channel (lane) inside the transceiver";
  }
  
  grouping l1-open-config-xcvr-logical-channel-base-config {
    description
      "Host facing ethernet stats";
  }
  
  grouping l1-open-config-xcvr-logical-channel-base-state {
    description
      "Host facing ethernet stats";
  }
  
  grouping l1-open-config-xcvr-logical-channel-state {
    description
      "Host facing ethernet stats";
  }
  
  grouping l1-open-config-xcvr-logical-channel-assignment-config {
    description
      "Container for the logical channel attributes";
  }
  
  grouping l1-open-config-xcvr-logical-channel-assignment-state {
    description
      "Host facing ethernet stats";
  }
  
  grouping l1-open-config-xcvr-logical-channel-intf-map {
    description
      "Host facing ethernet stats";
  }
  
  grouping l1-open-config-xcvr-logical-channel-ethernet-type {
    description
      "Host facing ethernet stats";
  }
  
  grouping l1-open-config-xcvr-logical-otn-channel-state {
    container q-margin {
      uses arista-l1-open-config-xcvr-oc-types:l1-open-config-xcvr-avg-min-max-instant-stats;
      description
        "qMargin";
    }
    description
      "Media stats in otn container";
  }
  
  grouping l1-open-config-xcvr-logical-channel-otn-type {
    description
      "Logical channel for otn stats";
  }
  
  grouping l1-open-config-xcvr-logical-channel-base-type {
    description
      "Host facing ethernet stats";
  }
  
  grouping l1-open-config-xcvr-logical-channel-config {
    description
      "Container for the logical channel base attributes";
  }
  
  grouping l1-open-config-xcvr-logical-channel-ingress-config {
    description
      "Container for the logical channel base attributes";
  }
  
  grouping l1-open-config-xcvr-logical-channel-ingress-state {
    description
      "Container for the logical channel base attributes";
  }
  
  grouping l1-open-config-xcvr-logical-channel {
    description
      "Container for the logical channel base attributes";
  }
  
  grouping l1-open-config-xcvr-logical-channel-assignment-type {
    description
      "Container for the logical channel attributes";
  }
  
  grouping l1-open-config-xcvr-logical-channel-config-assignment {
    description
      "Container for the logical channel attributes";
  }
  
  grouping l1-open-config-xcvr-logical-channel-assignment {
    description
      "Container for the logical channel attributes";
  }
  
  augment "/openconfig-platform:components/openconfig-platform:component/openconfig-terminal-device:optical-channel/openconfig-terminal-device:state" {
    container q-margin {
      uses arista-l1-open-config-xcvr-oc-types:l1-open-config-xcvr-avg-min-max-instant-stats;
      description
        "qMargin";
    }
    description
      "qMargin";
  }
  augment "/openconfig-terminal-device:terminal-device/openconfig-terminal-device:logical-channels/openconfig-terminal-device:channel/openconfig-terminal-device:otn/openconfig-terminal-device:state" {
    container q-margin {
      uses arista-l1-open-config-xcvr-oc-types:l1-open-config-xcvr-avg-min-max-instant-stats;
      description
        "qMargin";
    }
    description
      "qMargin";
  }
} // augmented-yang
