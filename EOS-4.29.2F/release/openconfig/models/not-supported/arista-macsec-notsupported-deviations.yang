module arista-macsec-notsupported-deviations {
  namespace "http://arista.com/yang/openconfig/macsec/notsupported-deviations";
  prefix arista-macsec-notsupported-deviations;

  import openconfig-macsec {
    prefix oc-macsec;
  }

  organization
    "Arista Networks, Inc.";
  contact
    "Arista Networks, Inc.
     Product Support";
  description
    "This module contains OpenConfig macsec deviations in Arista EOS.
     Copyright (c) 2022 Arista Networks, Inc. All rights reserved.";

  revision 2022-12-08 {
    description
      "Not-supported deviations file.";
  }
  revision 2022-11-19 {
    description
      "Not-supported deviations file.";
  }
  revision 2022-11-01 {
    description
      "Not-supported deviations file.";
  }
  revision 2022-10-07 {
    description
      "Not-supported deviations file.";
  }
  revision 2022-06-20 {
    description
      "Not-supported deviations file.";
  }

  deviation "/oc-macsec:macsec" {
    description
      "Not-supported deviation.";
    deviate not-supported;
  }
}
