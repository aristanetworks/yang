module arista-ebra-intf-encap {
  yang-version 1;
  namespace "http://arista.com/yang/experimental/eos/arista-ebra-intf-encap";
  prefix "arista-ebra-intf-encap";

  import openconfig-extensions { prefix "oc-ext"; }
  import arista-arnet-vlan-tag { prefix "arista-arnet-vlan-tag"; }
  import openconfig-interfaces { prefix "openconfig-interfaces"; }
  organization
    "Arista Networks <http://arista.com/>";
  contact
    "Arista Networks <http://arista.com/>";
  description
    "Defines encapsulations for interfaces

    THIS YANG MODULE WAS GENERATED. DO NOT EDIT THIS FILE.";

  oc-ext:openconfig-version "1.0.0";

  revision "2021-10-20" {
    description
      "Version 1.0.0, generated on 2021-10-20";
    reference "1.0.0";
  }

  grouping intf-vlan-encap {
    leaf intf-id {
      type openconfig-interfaces:interface-id;
      description
        "The interface";
    }
    container encap {
      uses arista-arnet-vlan-tag:ebra-vlan-tag-encap;
      description
        "The tag values to match or manipulate";
    }
    description
      "A local interface, dynamic tunnel or a pseudowire remote connector along with tag values to match or manipulate with";
  }

} // main-yang
