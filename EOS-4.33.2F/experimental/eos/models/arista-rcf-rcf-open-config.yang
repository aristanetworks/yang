module arista-rcf-rcf-open-config {
  yang-version 1;
  namespace "http://arista.com/yang/experimental/eos/arista-rcf-rcf-open-config";
  prefix "arista-rcf-rcf-open-config";

  import openconfig-extensions { prefix "oc-ext"; }
  import openconfig-routing-policy { prefix "openconfig-routing-policy"; }
  organization
    "Arista Networks <http://arista.com/>";
  contact
    "Arista Networks <http://arista.com/>";
  description
    "YANG models for RCF policy definitions.

    THIS YANG MODULE WAS GENERATED. DO NOT EDIT THIS FILE.";

  oc-ext:openconfig-version "1.0.0";

  revision "2023-09-12" {
    description
      "Version 1.0.0, generated on 2023-09-12";
    reference "1.0.0";
  }

  grouping rcf-open-config-rcf-config {
    leaf code {
      type string;
      description
        "Source code composing the RCF function definition";
    }
    leaf code-unit {
      type string;
      description
        "Code unit that contains the RCF function";
    }
    description
      "Grouping for RCF function definition configuration";
  }

  grouping rcf-open-config-rcf-container {
    container config {
      uses rcf-open-config-rcf-config;
      description
        "Configuration data for the RCF function definition";
    }
    container state {
      uses rcf-open-config-rcf-config;
      config false;
      description
        "Operational state for the RCF function definition";
    }
    description
      "Grouping for the RCF function definition container";
  }

  grouping rcf-open-config-rcf-dir {
    list rcf {
      key "name";
      uses rcf-open-config-rcf-container;
      description
        "Configuration data for the RCF function definition";
    }
    leaf name {
      type string;
      description
        "name of the grouping";
    }
    description
      "Top-level grouping for the RCF function definition configuration";
  }

  augment "/openconfig-routing-policy:routing-policy/openconfig-routing-policy:policy-definitions/openconfig-routing-policy:policy-definition" {
    container rcf {
     uses rcf-open-config-rcf-container;
     description
         "rcf container";
      }
  }
} // main-yang
