module arista-acl-acl-open-config-augment {
  yang-version 1;
  namespace "http://arista.com/yang/experimental/eos/arista-acl-acl-open-config-augment";
  prefix "arista-acl-acl-open-config-augment";

  import openconfig-extensions { prefix "oc-ext"; }
  import arista-acl-acl-open-config-icmpv4-types { prefix "arista-acl-acl-open-config-icmpv4-types"; }
  import arista-acl-acl-open-config-icmpv6-types { prefix "arista-acl-acl-open-config-icmpv6-types"; }
  import arista-acl-acl-open-config-packet-match-types { prefix "arista-acl-acl-open-config-packet-match-types"; }
  import openconfig-inet-types { prefix "openconfig-inet-types"; }
  import openconfig-packet-match-types { prefix "openconfig-packet-match-types"; }
  import openconfig-yang-types { prefix "openconfig-yang-types"; }
  import openconfig-acl { prefix "openconfig-acl"; }
  organization
    "Arista Networks <http://arista.com/>";
  contact
    "Arista Networks <http://arista.com/>";
  description
    "External tac model for traffic policy

    THIS YANG MODULE WAS GENERATED. DO NOT EDIT THIS FILE.";

  oc-ext:openconfig-version "1.0.0";

  revision "2024-07-19" {
    description
      "Version 1.0.0, generated on 2024-07-19";
    reference "1.0.0";
  }

  typedef acl-open-config-counter-action {
    type enumeration {
      enum COUNT_NONE {
        value 0;
        description
          "No counter for the acl-entry ";
      }
      enum COUNT {
        value 1;
        description
          "Counter enabled for the acl-entry ";
      }
    }
    description
      "acl-open-config-counter-action";
  }

  typedef acl-open-config-ocacl-mode {
    type enumeration {
      enum STATIC {
        value 0;
        description
          "Traffic policy config is added to the running-config";
      }
      enum CONTROLLER {
        value 1;
        description
          "Traffic Policy config populated by controller that isnon-persistent across reloads";
      }
    }
    description
      "Traffic Policy config mode";
  }

  grouping acl-open-config-ocacl-key {
    description
      "acl-open-config-ocacl-key";
  }

  grouping acl-open-config-ocacl-l2-config {
    description
      "acl-open-config-ocacl-l2-config";
  }

  grouping acl-open-config-ocacl-l2 {
    description
      "acl-open-config-ocacl-l2";
  }

  grouping acl-open-config-ocacl-icmpv4-config {
    description
      "acl-open-config-ocacl-icmpv4-config";
  }

  grouping acl-open-config-ocacl-icmpv4 {
    description
      "acl-open-config-ocacl-icmpv4";
  }

  grouping acl-open-config-ocacl-ip-common-config {
    description
      "acl-open-config-ocacl-ip-common-config";
  }

  grouping acl-open-config-ocacl-ipv4-config {
    uses acl-open-config-ocacl-ip-common-config;
    description
      "acl-open-config-ocacl-ipv4-config";
  }

  grouping acl-open-config-ocacl-ipv4 {
    description
      "acl-open-config-ocacl-ipv4";
  }

  grouping acl-open-config-ocacl-icmpv6-config {
    description
      "acl-open-config-ocacl-icmpv6-config";
  }

  grouping acl-open-config-ocacl-icmpv6 {
    description
      "acl-open-config-ocacl-icmpv6";
  }

  grouping acl-open-config-ocacl-ipv6-config {
    uses acl-open-config-ocacl-ip-common-config;
    description
      "acl-open-config-ocacl-ipv6-config";
  }

  grouping acl-open-config-ocacl-ipv6 {
    description
      "acl-open-config-ocacl-ipv6";
  }

  grouping acl-open-config-ocacl-transport-config {
    leaf-list source-port-list {
      type openconfig-packet-match-types:port-num-range;
      description
        "List of oc-pkt-match-types:port-num-range to match the source port";
    }
    leaf-list destination-port-list {
      type openconfig-packet-match-types:port-num-range;
      description
        "List of oc-pkt-match-types:port-num-range to match the destination port";
    }
    description
      "acl-open-config-ocacl-transport-config";
  }

  augment "/openconfig-acl:acl/openconfig-acl:acl-sets/openconfig-acl:acl-set/openconfig-acl:acl-entries/openconfig-acl:acl-entry/openconfig-acl:transport/openconfig-acl:config" {
    leaf-list source-port-list {
      type openconfig-packet-match-types:port-num-range;
      description
        "List of oc-pkt-match-types:port-num-range to match the source port";
    }
    leaf-list destination-port-list {
      type openconfig-packet-match-types:port-num-range;
      description
        "List of oc-pkt-match-types:port-num-range to match the destination port";
    }
    description
      "";
  }
  augment "/openconfig-acl:acl/openconfig-acl:acl-sets/openconfig-acl:acl-set/openconfig-acl:acl-entries/openconfig-acl:acl-entry/openconfig-acl:transport/openconfig-acl:state" {
    leaf-list source-port-list {
      type openconfig-packet-match-types:port-num-range;
      description
        "List of oc-pkt-match-types:port-num-range to match the source port";
    }
    leaf-list destination-port-list {
      type openconfig-packet-match-types:port-num-range;
      description
        "List of oc-pkt-match-types:port-num-range to match the destination port";
    }
    description
      "";
  }
  grouping acl-open-config-ocacl-transport {
    description
      "acl-open-config-ocacl-transport";
  }

  grouping acl-open-config-counter {
    leaf count-action {
      type acl-open-config-counter-action;
      default COUNT_NONE;
      description
        "No counter for the acl-entry ";
    }
    description
      "Add a counter on an acl-entry ";
  }

  grouping acl-open-config-ocacl-actions-config {
    container counter {
      uses acl-open-config-counter;
      oc-ext:telemetry-atomic;
      description
        "counter";
    }
    description
      "acl-open-config-ocacl-actions-config";
  }

  augment "/openconfig-acl:acl/openconfig-acl:acl-sets/openconfig-acl:acl-set/openconfig-acl:acl-entries/openconfig-acl:acl-entry/openconfig-acl:actions/openconfig-acl:config" {
    container counter {
      uses acl-open-config-counter;
      oc-ext:telemetry-atomic;
      description
        "counter";
    }
    description
      "";
  }
  augment "/openconfig-acl:acl/openconfig-acl:acl-sets/openconfig-acl:acl-set/openconfig-acl:acl-entries/openconfig-acl:acl-entry/openconfig-acl:actions/openconfig-acl:state" {
    container counter {
      uses acl-open-config-counter;
      oc-ext:telemetry-atomic;
      description
        "counter";
    }
    description
      "";
  }
  grouping acl-open-config-ocacl-actions {
    description
      "acl-open-config-ocacl-actions";
  }

  grouping acl-open-config-ocacl-entry-config {
    description
      "acl-open-config-ocacl-entry-config";
  }

  grouping acl-open-config-ocacl-entry {
    description
      "acl-open-config-ocacl-entry";
  }

  grouping acl-open-config-ocacl-entries {
    description
      "acl-open-config-ocacl-entries";
  }

  grouping acl-open-config-ocacl-set-config {
    leaf mode {
      type acl-open-config-ocacl-mode;
      default STATIC;
      description
        "mode";
    }
    description
      "acl-open-config-ocacl-set-config";
  }

  augment "/openconfig-acl:acl/openconfig-acl:acl-sets/openconfig-acl:acl-set/openconfig-acl:config" {
    leaf mode {
      type acl-open-config-ocacl-mode;
      default STATIC;
      description
        "mode";
    }
    description
      "";
  }
  augment "/openconfig-acl:acl/openconfig-acl:acl-sets/openconfig-acl:acl-set/openconfig-acl:state" {
    leaf mode {
      type acl-open-config-ocacl-mode;
      default STATIC;
      description
        "mode";
    }
    description
      "";
  }
  grouping acl-open-config-ocacl-set {
    description
      "acl-open-config-ocacl-set";
  }

  grouping acl-open-config-ocacl-sets {
    description
      "";
  }

  grouping acl-open-config-ocacl-state {
    description
      "";
  }

} // augmented-yang
