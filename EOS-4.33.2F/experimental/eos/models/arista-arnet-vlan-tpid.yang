module arista-arnet-vlan-tpid {
  yang-version 1;
  namespace "http://arista.com/yang/experimental/eos/arista-arnet-vlan-tpid";
  prefix "arista-arnet-vlan-tpid";

  import openconfig-extensions { prefix "oc-ext"; }
  organization
    "Arista Networks <http://arista.com/>";
  contact
    "Arista Networks <http://arista.com/>";
  description
    "Models for the TPID field in VLAN headers according to IEEE 802.1Q and IEEE 802.1ad

    THIS YANG MODULE WAS GENERATED. DO NOT EDIT THIS FILE.";

  oc-ext:openconfig-version "1.0.0";

  revision "2021-10-20" {
    description
      "Version 1.0.0, generated on 2021-10-20";
    reference "1.0.0";
  }

  typedef bridging-vlan-tpid {
    type uint16;
    default 33024;
    description
      "A tag protocol identifier (TPID)";
  }

} // main-yang
