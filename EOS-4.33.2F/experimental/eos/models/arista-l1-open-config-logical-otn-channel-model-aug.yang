module arista-l1-open-config-logical-otn-channel-model-aug {
  yang-version 1;
  namespace "http://arista.com/yang/experimental/eos/arista-l1-open-config-logical-otn-channel-model-aug";
  prefix "arista-l1-open-config-logical-otn-channel-model-aug";

  import openconfig-extensions { prefix "oc-ext"; }
  import arista-l1-open-config-xcvr-oc-types { prefix "arista-l1-open-config-xcvr-oc-types"; }
  import openconfig-terminal-device { prefix "openconfig-terminal-device"; }
  organization
    "Arista Networks <http://arista.com/>";
  contact
    "Arista Networks <http://arista.com/>";
  description
    "Logical channel OTN state parameters

    THIS YANG MODULE WAS GENERATED. DO NOT EDIT THIS FILE.";

  oc-ext:openconfig-version "1.0.0";

  revision "2022-05-12" {
    description
      "Version 1.0.0, generated on 2022-05-12";
    reference "1.0.0";
  }

  grouping l1-open-config-xcvr-logical-otn-channel-state-aug {
    leaf index {
      type uint32;
      description
        "Arbitrary index of logical channel";
    }
    container q-margin {
      uses arista-l1-open-config-xcvr-oc-types:l1-open-config-xcvr-avg-min-max-instant-stats;
      description
        "qMargin";
    }
    leaf name {
      type string;
      description
        "name of the grouping";
    }
    description
      "Augments for logical channel otn state attributes";
  }

  grouping l1-open-config-xcvr-logical-otn-channel-aug {
    list state {
      key "index";
      uses l1-open-config-xcvr-logical-otn-channel-state-aug;
      description
        "Augments of logical channel otn attributes";
    }
    leaf name {
      type string;
      description
        "name of the grouping";
    }
    description
      "Container for augmented optical channel states";
  }

  augment "/openconfig-terminal-device:terminal-device/openconfig-terminal-device:logical-channels/openconfig-terminal-device:channel/openconfig-terminal-device:otn/openconfig-terminal-device:state" {
     uses l1-open-config-xcvr-logical-otn-channel-state-aug;
}
} // main-yang
