module arista-ale-counters-open-config-interrupt-counters {
  yang-version 1;
  namespace "http://arista.com/yang/experimental/eos/arista-ale-counters-open-config-interrupt-counters";
  prefix "arista-ale-counters-open-config-interrupt-counters";

  import openconfig-extensions { prefix "oc-ext"; }
  import openconfig-platform { prefix "openconfig-platform"; }
  organization
    "Arista Networks <http://arista.com/>";
  contact
    "Arista Networks <http://arista.com/>";
  description
    "Interrupt counters

    THIS YANG MODULE WAS GENERATED. DO NOT EDIT THIS FILE.";

  oc-ext:openconfig-version "1.0.0";

  revision "2021-10-20" {
    description
      "Version 1.0.0, generated on 2021-10-20";
    reference "1.0.0";
  }

  grouping ale-counters-open-config-interrupt-sand-counters {
    leaf total-interrupt-counters {
      type uint64;
      description
        "Sample interrupt counter.";
    }
    description
      "Container for Sand specific interrupt counters.";
  }

  grouping ale-counters-open-config-interrupt-counters {
    container sand {
      uses ale-counters-open-config-interrupt-sand-counters;
      description
        "Container for Sand specific interrupt counters.";
    }
    leaf name {
      type string;
      description
        "name of the grouping";
    }
    description
      "";
  }

  grouping ale-counters-open-config-interrupt {
    list interrupt-counters {
      key "name";
      uses ale-counters-open-config-interrupt-counters;
      description
        "";
    }
    leaf name {
      type string;
      description
        "name of the grouping";
    }
    description
      "";
  }

  augment "/openconfig-platform:components/openconfig-platform:component/openconfig-platform:integrated-circuit" {
    container interrupt-counters {
      container vendor {
        container arista {
          config false;
     uses ale-counters-open-config-interrupt-counters;
     description
         "arista container";
      }
       description
         "vendor container";
      }
       description
         "interrupt-counters container";
      }
  }
} // main-yang
