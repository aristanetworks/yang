module arista-acl-acl-open-config-icmpv4-types {
  yang-version 1;
  namespace "http://arista.com/yang/experimental/eos/arista-acl-acl-open-config-icmpv4-types";
  prefix "arista-acl-acl-open-config-icmpv4-types";

  import openconfig-extensions { prefix "oc-ext"; }
  organization
    "Arista Networks <http://arista.com/>";
  contact
    "Arista Networks <http://arista.com/>";
  description
    "Identity types relating to icmpv4

    THIS YANG MODULE WAS GENERATED. DO NOT EDIT THIS FILE.";

  oc-ext:openconfig-version "1.0.0";

  revision "2024-07-19" {
    description
      "Version 1.0.0, generated on 2024-07-19";
    reference "1.0.0";
  }

  // covered-by: openconfig-icmpv4-types.yang
  identity ACL_OPEN_CONFIG_OCICMPV_4_TYPE {
    description
      "acl-open-config-ocicmpv4-type";
  }
  identity ECHO_RELY {
    base "ACL_OPEN_CONFIG_OCICMPV_4_TYPE";
    description
      "ECHO_RELY";
  }
  identity DST_UNREACHABLE {
    base "ACL_OPEN_CONFIG_OCICMPV_4_TYPE";
    description
      "DST_UNREACHABLE";
  }
  identity REDIRECT {
    base "ACL_OPEN_CONFIG_OCICMPV_4_TYPE";
    description
      "REDIRECT";
  }
  identity ECHO {
    base "ACL_OPEN_CONFIG_OCICMPV_4_TYPE";
    description
      "ECHO";
  }
  identity ROUTER_ADVERTISEMENT {
    base "ACL_OPEN_CONFIG_OCICMPV_4_TYPE";
    description
      "ROUTER_ADVERTISEMENT";
  }
  identity ROUTER_SOLICITATION {
    base "ACL_OPEN_CONFIG_OCICMPV_4_TYPE";
    description
      "ROUTER_SOLICITATION";
  }
  identity TIME_EXCEEDED {
    base "ACL_OPEN_CONFIG_OCICMPV_4_TYPE";
    description
      "TIME_EXCEEDED";
  }
  identity PARAM_PROBLEM {
    base "ACL_OPEN_CONFIG_OCICMPV_4_TYPE";
    description
      "PARAM_PROBLEM";
  }
  identity TIME_STAMP {
    base "ACL_OPEN_CONFIG_OCICMPV_4_TYPE";
    description
      "TIME_STAMP";
  }
  identity TIME_STAMP_REPLY {
    base "ACL_OPEN_CONFIG_OCICMPV_4_TYPE";
    description
      "TIME_STAMP_REPLY";
  }
  identity TRACE_ROUTE {
    base "ACL_OPEN_CONFIG_OCICMPV_4_TYPE";
    description
      "TRACE_ROUTE";
  }
  identity PHOTURIS {
    base "ACL_OPEN_CONFIG_OCICMPV_4_TYPE";
    description
      "PHOTURIS";
  }
  identity EXT_ECHO_REQUEST {
    base "ACL_OPEN_CONFIG_OCICMPV_4_TYPE";
    description
      "EXT_ECHO_REQUEST";
  }
  identity EXT_ECHO_REPLY {
    base "ACL_OPEN_CONFIG_OCICMPV_4_TYPE";
    description
      "EXT_ECHO_REPLY";
  }
  identity ACL_OPEN_CONFIG_OCICMPV_4_CODE {
    description
      "acl-open-config-ocicmpv4-code";
  }
  identity ECHO_REPLY_NONE {
    base "ACL_OPEN_CONFIG_OCICMPV_4_CODE";
    description
      "ECHO_REPLY_NONE";
  }
  identity DST_UNREACHABLE_NET {
    base "ACL_OPEN_CONFIG_OCICMPV_4_CODE";
    description
      "DST_UNREACHABLE_NET";
  }
  identity DST_UNREACHABLE_HOST {
    base "ACL_OPEN_CONFIG_OCICMPV_4_CODE";
    description
      "DST_UNREACHABLE_HOST";
  }
  identity DST_UNREACHABLE_PROTOCOL {
    base "ACL_OPEN_CONFIG_OCICMPV_4_CODE";
    description
      "DST_UNREACHABLE_PROTOCOL";
  }
  identity DST_UNREACHABLE_PORT {
    base "ACL_OPEN_CONFIG_OCICMPV_4_CODE";
    description
      "DST_UNREACHABLE_PORT";
  }
  identity DST_UNREACHABLE_CANNOT_FRAGMENT {
    base "ACL_OPEN_CONFIG_OCICMPV_4_CODE";
    description
      "DST_UNREACHABLE_CANNOT_FRAGMENT";
  }
  identity DST_UNREACHABLE_SRC_ROUTE_FAILED {
    base "ACL_OPEN_CONFIG_OCICMPV_4_CODE";
    description
      "DST_UNREACHABLE_SRC_ROUTE_FAILED";
  }
  identity DST_UNREACHABLE_DST_NET_UNKNOWN {
    base "ACL_OPEN_CONFIG_OCICMPV_4_CODE";
    description
      "DST_UNREACHABLE_DST_NET_UNKNOWN";
  }
  identity DST_UNREACHABLE_DST_HOST_UNKNOWN {
    base "ACL_OPEN_CONFIG_OCICMPV_4_CODE";
    description
      "DST_UNREACHABLE_DST_HOST_UNKNOWN";
  }
  identity DST_UNREACHABLE_SRC_HOST_ISOLATED {
    base "ACL_OPEN_CONFIG_OCICMPV_4_CODE";
    description
      "DST_UNREACHABLE_SRC_HOST_ISOLATED";
  }
  identity DST_UNREACHABLE_DST_NET_ADMIN_PROHIBITED {
    base "ACL_OPEN_CONFIG_OCICMPV_4_CODE";
    description
      "DST_UNREACHABLE_DST_NET_ADMIN_PROHIBITED";
  }
  identity DST_UNREACHABLE_DST_HOST_ADMIN_PROHIBITED {
    base "ACL_OPEN_CONFIG_OCICMPV_4_CODE";
    description
      "DST_UNREACHABLE_DST_HOST_ADMIN_PROHIBITED";
  }
  identity DST_UNREACHABLE_NET_UNREACHABLE_FOR_TOS {
    base "ACL_OPEN_CONFIG_OCICMPV_4_CODE";
    description
      "DST_UNREACHABLE_NET_UNREACHABLE_FOR_TOS";
  }
  identity DST_UNREACHABLE_HOST_UNREACHABLE_FOR_TOS {
    base "ACL_OPEN_CONFIG_OCICMPV_4_CODE";
    description
      "DST_UNREACHABLE_HOST_UNREACHABLE_FOR_TOS";
  }
  identity DST_UNREACHABLE_ADMIN_PROHIBITED {
    base "ACL_OPEN_CONFIG_OCICMPV_4_CODE";
    description
      "DST_UNREACHABLE_ADMIN_PROHIBITED";
  }
  identity DST_UNREACHABLE_HOST_PRECEDENCE_VIOLATION {
    base "ACL_OPEN_CONFIG_OCICMPV_4_CODE";
    description
      "DST_UNREACHABLE_HOST_PRECEDENCE_VIOLATION";
  }
  identity DST_UNREACHABLE_PRECEDENCE_CUTOFF {
    base "ACL_OPEN_CONFIG_OCICMPV_4_CODE";
    description
      "DST_UNREACHABLE_PRECEDENCE_CUTOFF";
  }
  identity REDIRECT_NETWORK {
    base "ACL_OPEN_CONFIG_OCICMPV_4_CODE";
    description
      "REDIRECT_NETWORK";
  }
  identity REDIRECT_HOST {
    base "ACL_OPEN_CONFIG_OCICMPV_4_CODE";
    description
      "REDIRECT_HOST";
  }
  identity REDIRECT_TOS_NETWORK {
    base "ACL_OPEN_CONFIG_OCICMPV_4_CODE";
    description
      "REDIRECT_TOS_NETWORK";
  }
  identity REDIRECT_TOS_HOST {
    base "ACL_OPEN_CONFIG_OCICMPV_4_CODE";
    description
      "REDIRECT_TOS_HOST";
  }
  identity ECHO_NO_CODE {
    base "ACL_OPEN_CONFIG_OCICMPV_4_CODE";
    description
      "ECHO_NO_CODE";
  }
  identity ROUTER_ADVERTISEMENT_NORMAL {
    base "ACL_OPEN_CONFIG_OCICMPV_4_CODE";
    description
      "ROUTER_ADVERTISEMENT_NORMAL";
  }
  identity ROUTER_ADVERTISEMENT_DOES_NOT_ROUTE_COMMON {
    base "ACL_OPEN_CONFIG_OCICMPV_4_CODE";
    description
      "ROUTER_ADVERTISEMENT_DOES_NOT_ROUTE_COMMON";
  }
  identity ROUTER_SELECTION_NO_CODE {
    base "ACL_OPEN_CONFIG_OCICMPV_4_CODE";
    description
      "ROUTER_SELECTION_NO_CODE";
  }
  identity TIME_EXCEEDED_IN_TRANSIT {
    base "ACL_OPEN_CONFIG_OCICMPV_4_CODE";
    description
      "TIME_EXCEEDED_IN_TRANSIT";
  }
  identity TIME_EXCEEDED_FRAGMENT_REASSEMBLY_IN_TRANSIT {
    base "ACL_OPEN_CONFIG_OCICMPV_4_CODE";
    description
      "TIME_EXCEEDED_FRAGMENT_REASSEMBLY_IN_TRANSIT";
  }
  identity PARAM_PROBLEM_POINTER_INDICATES_ERR {
    base "ACL_OPEN_CONFIG_OCICMPV_4_CODE";
    description
      "PARAM_PROBLEM_POINTER_INDICATES_ERR";
  }
  identity PARAM_PROBLEM_MISSING_REQ_OPTION {
    base "ACL_OPEN_CONFIG_OCICMPV_4_CODE";
    description
      "PARAM_PROBLEM_MISSING_REQ_OPTION";
  }
  identity PARAM_PROBLEM_BAD_LENGTH {
    base "ACL_OPEN_CONFIG_OCICMPV_4_CODE";
    description
      "PARAM_PROBLEM_BAD_LENGTH";
  }
  identity TIMESTAMP_NO_CODE {
    base "ACL_OPEN_CONFIG_OCICMPV_4_CODE";
    description
      "TIMESTAMP_NO_CODE";
  }
  identity TIMESTAMP_REPLY_NO_CODE {
    base "ACL_OPEN_CONFIG_OCICMPV_4_CODE";
    description
      "TIMESTAMP_REPLY_NO_CODE";
  }
  identity PHOTURIS_BAD_SPI {
    base "ACL_OPEN_CONFIG_OCICMPV_4_CODE";
    description
      "PHOTURIS_BAD_SPI";
  }
  identity PHOTURIS_AUTH_FAILED {
    base "ACL_OPEN_CONFIG_OCICMPV_4_CODE";
    description
      "PHOTURIS_AUTH_FAILED";
  }
  identity PHOTURIS_DECOMPRESS_FAILED {
    base "ACL_OPEN_CONFIG_OCICMPV_4_CODE";
    description
      "PHOTURIS_DECOMPRESS_FAILED";
  }
  identity PHOTURIS_DECRYPTION_FAILED {
    base "ACL_OPEN_CONFIG_OCICMPV_4_CODE";
    description
      "PHOTURIS_DECRYPTION_FAILED";
  }
  identity PHOTURIS_NEED_AUTHENTICATION {
    base "ACL_OPEN_CONFIG_OCICMPV_4_CODE";
    description
      "PHOTURIS_NEED_AUTHENTICATION";
  }
  identity PHOTURIS_NEED_AUTHORIZATION {
    base "ACL_OPEN_CONFIG_OCICMPV_4_CODE";
    description
      "PHOTURIS_NEED_AUTHORIZATION";
  }
  identity EXT_ECHO_REQUEST_NO_ERROR {
    base "ACL_OPEN_CONFIG_OCICMPV_4_CODE";
    description
      "EXT_ECHO_REQUEST_NO_ERROR";
  }
  identity EXT_ECHO_REPLY_NO_ERROR {
    base "ACL_OPEN_CONFIG_OCICMPV_4_CODE";
    description
      "EXT_ECHO_REPLY_NO_ERROR";
  }
  identity EXT_ECHO_REPLY_MALFORMED_QUERY {
    base "ACL_OPEN_CONFIG_OCICMPV_4_CODE";
    description
      "EXT_ECHO_REPLY_MALFORMED_QUERY";
  }
  identity EXT_ECHO_REPLY_NO_SUCH_INTF {
    base "ACL_OPEN_CONFIG_OCICMPV_4_CODE";
    description
      "EXT_ECHO_REPLY_NO_SUCH_INTF";
  }
  identity EXT_ECHO_REPLY_NO_SUB_TABLE_ENTRY {
    base "ACL_OPEN_CONFIG_OCICMPV_4_CODE";
    description
      "EXT_ECHO_REPLY_NO_SUB_TABLE_ENTRY";
  }
  identity EXT_ECHO_REPLY_MULTIPLE_INTF_SATISFY_QUERY {
    base "ACL_OPEN_CONFIG_OCICMPV_4_CODE";
    description
      "EXT_ECHO_REPLY_MULTIPLE_INTF_SATISFY_QUERY";
  }
} // main-yang
