module arista-ale-counters-open-config-control-plane-traffic-counters {
  yang-version 1;
  namespace "http://arista.com/yang/experimental/eos/arista-ale-counters-open-config-control-plane-traffic-counters";
  prefix "arista-ale-counters-open-config-control-plane-traffic-counters";

  import openconfig-extensions { prefix "oc-ext"; }
  organization
    "Arista Networks <http://arista.com/>";
  contact
    "Arista Networks <http://arista.com/>";
  description
    "Vendor-specific control-plane traffic counters

    THIS YANG MODULE WAS GENERATED. DO NOT EDIT THIS FILE.";

  oc-ext:openconfig-version "1.0.0";

  revision "2023-02-02" {
    description
      "Version 1.0.0, generated on 2023-02-02";
    reference "1.0.0";
  }

  grouping ale-counters-open-config-control-plane-traffic-counters {
    leaf queued {
      type uint64;
      description
        "This counter counts the number of packets enqueued.";
    }
    leaf queued-bytes {
      type uint64;
      description
        "This counter counts the number of bytes enqueued.";
    }
    leaf dropped {
      type uint64;
      description
        "This counter counts the number of packets dropped.";
    }
    leaf dropped-bytes {
      type uint64;
      description
        "This counter counts the number of bytes dropped.";
    }
    description
      "Container for Sand specific control-plane traffic counters.";
  }

  grouping ale-counters-open-config-control-plane-traffic-counters-state {
    container acl-log {
      uses ale-counters-open-config-control-plane-traffic-counters;
      description
        "Control-plane traffic for ACL entries that deny traffic with logging.";
    }
    container arp-inspect {
      uses ale-counters-open-config-control-plane-traffic-counters;
      description
        "Control-plane traffic for ARP inspect feature.";
    }
    container bfd {
      uses ale-counters-open-config-control-plane-traffic-counters;
      description
        "Control-plane traffic for BFD.";
    }
    container bgp {
      uses ale-counters-open-config-control-plane-traffic-counters;
      description
        "Control-plane traffic for BGP.";
    }
    container bpdu {
      uses ale-counters-open-config-control-plane-traffic-counters;
      description
        "Control-plane traffic for MSTP, RSTP, Rapid PVST BPDUs.";
    }
    container cfm {
      uses ale-counters-open-config-control-plane-traffic-counters;
      description
        "Control-plane traffic for connectivity fault management (CFM) protocol.";
    }
    container cfm-snoop {
      uses ale-counters-open-config-control-plane-traffic-counters;
      description
        "Control-plane traffic for CFM snooping.";
    }
    container cvx {
      uses ale-counters-open-config-control-plane-traffic-counters;
      description
        "Control-plane traffic for CloudVision.";
    }
    container cvx-heartbeat {
      uses ale-counters-open-config-control-plane-traffic-counters;
      description
        "Control-plane traffic for CVX keep alives.";
    }
    container dot1x-mba {
      uses ale-counters-open-config-control-plane-traffic-counters;
      description
        "Control-plane traffic for 802.1X MBA.";
    }
    container eapol {
      uses ale-counters-open-config-control-plane-traffic-counters;
      description
        "Control-plane traffic for EAPOL.";
    }
    container egress-trap {
      uses ale-counters-open-config-control-plane-traffic-counters;
      description
        "Control-plane traffic for MTU violating packets.";
    }
    container igmp {
      uses ale-counters-open-config-control-plane-traffic-counters;
      description
        "Control-plane traffic for IGMP.";
    }
    container ip-broadcast {
      uses ale-counters-open-config-control-plane-traffic-counters;
      description
        "Control-plane traffic for IP broadcast packets that are destined for the all-broadcast address (.255).";
    }
    container ip-multicast {
      uses ale-counters-open-config-control-plane-traffic-counters;
      description
        "Control-plane traffic for multicast IP packets received by a PIM Designated Router (DR) and forwarded.";
    }
    container ip-multicast-miss {
      uses ale-counters-open-config-control-plane-traffic-counters;
      description
        "Control-plane traffic for multicast IP packets and have missed their multicast routing lookup. ";
    }
    container ip-unicast {
      uses ale-counters-open-config-control-plane-traffic-counters;
      description
        "Control-plane traffic for any IP packet that does not match a specific protocol queue.";
    }
    container l2-broadcast {
      uses ale-counters-open-config-control-plane-traffic-counters;
      description
        "Control-plane traffic for Layer 2 broadcast packets, such as ARP, DHCP packets received on L3 VLAN.";
    }
    container l2-unicast {
      uses ale-counters-open-config-control-plane-traffic-counters;
      description
        "Control-plane traffic for Layer 2 unicast Ethernet packets and ARP reply packets that are destined for the router's MAC address on an L3-enabled interface.";
    }
    container l3-destination-miss {
      uses ale-counters-open-config-control-plane-traffic-counters;
      description
        "Control-plane traffic for Layer 3 destination miss, such as traffic that is sent to a subnet configured on the device but cannot be routed due to a missing route, resulting in an 'unroutable' or 'destination host unreachable' status.";
    }
    container l3-lpm-overflow {
      uses ale-counters-open-config-control-plane-traffic-counters;
      description
        "Control-plane traffic that hits the default route, or routed traffic that results in an 'unroutable' or 'destination network unreachable' status. This traffic triggers the CPU to send an ICMP unreachable message back to the sender.";
    }
    container l3-ttl1-ip-opt-unicast {
      uses ale-counters-open-config-control-plane-traffic-counters;
      description
        "Control-plane traffic for unicast routed packets with TTL=1 and IP packets that contain options.";
    }
    container l3-ttl1-ip-options {
      uses ale-counters-open-config-control-plane-traffic-counters;
      description
        "Control-plane traffic for multicast routed packets with TTL value of 1 and multicast packets that contain options.";
    }
    container lacp {
      uses ale-counters-open-config-control-plane-traffic-counters;
      description
        "Control-plane traffic for LACP.";
    }
    container ldp {
      uses ale-counters-open-config-control-plane-traffic-counters;
      description
        "Control-plane traffic for LDP.";
    }
    container link-local {
      uses ale-counters-open-config-control-plane-traffic-counters;
      description
        "Control-plane traffic for link-local multicast packets, this includes IPv6 link-local range as well as IPv4 224.0.0./24 multicast address range.";
    }
    container link-local-src {
      uses ale-counters-open-config-control-plane-traffic-counters;
      description
        "Control-plane traffic for IPv6 packets with link-local source address. These packets should not be routed.";
    }
    container lldp {
      uses ale-counters-open-config-control-plane-traffic-counters;
      description
        "Control-plane traffic for LLDP.";
    }
    container mirroring {
      uses ale-counters-open-config-control-plane-traffic-counters;
      description
        "Control-plane traffic coming from monitor session with destination set to CPU.";
    }
    container mlag {
      uses ale-counters-open-config-control-plane-traffic-counters;
      description
        "Control-plane traffic for MLAG.";
    }
    container mpls-arp-suppress {
      uses ale-counters-open-config-control-plane-traffic-counters;
      description
        "Control-plane traffic for MPLS ARP suppressed packets. These packets are prevented from being encapsulated in hardware and are instead encapsulated in software as needed.";
    }
    container mpls-label-miss {
      uses ale-counters-open-config-control-plane-traffic-counters;
      description
        "Control-plane traffic for MPLS packets with an MPLS label that does not match any known label in the network, potentially caused by the absence of a FIB entry for the MPLS label.";
    }
    container mpls-ttl {
      uses ale-counters-open-config-control-plane-traffic-counters;
      description
        "Control-plane traffic for MPLS packets with TTL=0 or TTL=1.";
    }
    container multicast-snoop {
      uses ale-counters-open-config-control-plane-traffic-counters;
      description
        "Control-plane traffic for multicast snooping. This type of traffic is triggered by specific cases involving IGMP and PIM, including PIM hellos, and is only active when IgmpSnooping and Pim are enabled.";
    }
    container mvrp {
      uses ale-counters-open-config-control-plane-traffic-counters;
      description
        "Control-plane traffic for Multiple VLAN Registration Protocol (MVRP).";
    }
    container ospf-isis {
      uses ale-counters-open-config-control-plane-traffic-counters;
      description
        "Control-plane traffic for multicast OSPF or ISIS updates.";
    }
    container ospf-isis-unicast {
      uses ale-counters-open-config-control-plane-traffic-counters;
      description
        "Control-plane traffic for unicast OSPF, ISIS.";
    }
    container ptp {
      uses ale-counters-open-config-control-plane-traffic-counters;
      description
        "Control-plane traffic for PTP.";
    }
    container ptp-snoop {
      uses ale-counters-open-config-control-plane-traffic-counters;
      description
        "Control-plane traffic for PTP snooping.";
    }
    container rsvp {
      uses ale-counters-open-config-control-plane-traffic-counters;
      description
        "Control-plane traffic for RSVP.";
    }
    container sflow {
      uses ale-counters-open-config-control-plane-traffic-counters;
      description
        "Control-plane traffic for sFlow samples.";
    }
    container vxlan-encap {
      uses ale-counters-open-config-control-plane-traffic-counters;
      description
        "Control-plane traffic for native packets that need to be VXLAN encapsulated in software.";
    }
    container vxlan-vtep-learn {
      uses ale-counters-open-config-control-plane-traffic-counters;
      description
        "Control-plane traffic for VXLAN encapsulated packets for which the source VTEP has not been learned.";
    }
    description
      "Container for Sand specific control-plane traffic counters.";
  }

  grouping ale-counters-open-config-pipeline-arista-sand-control-plane-traffic-counters {
    container state {
      uses ale-counters-open-config-control-plane-traffic-counters-state;
      description
        "";
    }
    description
      "Container for Sand specific control-plane traffic counters.";
  }

  grouping ale-counters-open-config-pipeline-arista-control-plane-traffic-counters {
    container sand {
      uses ale-counters-open-config-pipeline-arista-sand-control-plane-traffic-counters;
      description
        "Container for Sand specific control-plane traffic counters.";
    }
    description
      "";
  }

  grouping ale-counters-open-config-pipeline-vendor-control-plane-traffic-counters {
    container arista {
      uses ale-counters-open-config-pipeline-arista-control-plane-traffic-counters;
      description
        "Container for Arista-specific control-plane traffic counters.";
    }
    description
      "";
  }

} // main-yang
