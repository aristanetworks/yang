module arista-network-instance-notsupported-deviations {
  namespace "http://arista.com/yang/openconfig/network-instance/notsupported-deviations";
  prefix arista-network-instance-notsupported-deviations;

  import openconfig-aft-network-instance {
    prefix oc-aftni;
  }
  import openconfig-flexalgo {
    prefix oc-flexalgo;
  }
  import openconfig-isis-flex-algo {
    prefix flex-algo;
  }
  import openconfig-network-instance {
    prefix oc-netinst;
  }
  import openconfig-pf-srte {
    prefix oc-pf-srte;
  }
  import openconfig-programming-errors {
    prefix oc-pgrmerrs;
  }

  organization
    "Arista Networks, Inc.";
  contact
    "Arista Networks, Inc.
     Product Support";
  description
    "This module contains OpenConfig network-instance deviations in Arista EOS.
     Copyright (c) 2020 Arista Networks, Inc. All rights reserved.";

  revision 2025-02-12 {
    description
      "Auto-generated not-supported deviations for unsupported paths";
  }

  deviation "/oc-netinst:network-instances/oc-netinst:network-instance/flex-algo:flex-algo" {
    description
      "Not-supported deviation.";
    deviate not-supported;
  }

  deviation "/oc-netinst:network-instances/oc-netinst:network-instance/oc-netinst:connection-points" {
    description
      "Not-supported deviation.";
    deviate not-supported;
  }

  deviation "/oc-netinst:network-instances/oc-netinst:network-instance/oc-netinst:encapsulation" {
    description
      "Not-supported deviation.";
    deviate not-supported;
  }

  deviation "/oc-netinst:network-instances/oc-netinst:network-instance/oc-netinst:evpn" {
    description
      "Not-supported deviation.";
    deviate not-supported;
  }

  deviation "/oc-netinst:network-instances/oc-netinst:network-instance/oc-netinst:route-limits" {
    description
      "Not-supported deviation.";
    deviate not-supported;
  }

  deviation "/oc-netinst:network-instances/oc-netinst:network-instance/oc-flexalgo:flex-algorithm/oc-flexalgo:flex-algo-global-attributes" {
    description
      "Not-supported deviation.";
    deviate not-supported;
  }

  deviation "/oc-netinst:network-instances/oc-netinst:network-instance/oc-flexalgo:flex-algorithm/oc-flexalgo:flex-algo-interface-attributes" {
    description
      "Not-supported deviation.";
    deviate not-supported;
  }

  deviation "/oc-netinst:network-instances/oc-netinst:network-instance/oc-flexalgo:flex-algorithm/oc-flexalgo:flex-algorithm-definition/oc-flexalgo:algorithm/oc-flexalgo:config/oc-flexalgo:algo-flags" {
    description
      "Not-supported deviation.";
    deviate not-supported;
  }

  deviation "/oc-netinst:network-instances/oc-netinst:network-instance/oc-flexalgo:flex-algorithm/oc-flexalgo:flex-algorithm-definition/oc-flexalgo:algorithm/oc-flexalgo:config/oc-flexalgo:calc-type" {
    description
      "Not-supported deviation.";
    deviate not-supported;
  }

  deviation "/oc-netinst:network-instances/oc-netinst:network-instance/oc-flexalgo:flex-algorithm/oc-flexalgo:flex-algorithm-definition/oc-flexalgo:algorithm/oc-flexalgo:config/oc-flexalgo:flex-algo-description" {
    description
      "Not-supported deviation.";
    deviate not-supported;
  }

  deviation "/oc-netinst:network-instances/oc-netinst:network-instance/oc-flexalgo:flex-algorithm/oc-flexalgo:flex-algorithm-definition/oc-flexalgo:algorithm/oc-flexalgo:state/oc-flexalgo:algo-flags" {
    description
      "Not-supported deviation.";
    deviate not-supported;
  }

  deviation "/oc-netinst:network-instances/oc-netinst:network-instance/oc-flexalgo:flex-algorithm/oc-flexalgo:flex-algorithm-definition/oc-flexalgo:algorithm/oc-flexalgo:state/oc-flexalgo:calc-type" {
    description
      "Not-supported deviation.";
    deviate not-supported;
  }

  deviation "/oc-netinst:network-instances/oc-netinst:network-instance/oc-flexalgo:flex-algorithm/oc-flexalgo:flex-algorithm-definition/oc-flexalgo:algorithm/oc-flexalgo:state/oc-flexalgo:flex-algo-description" {
    description
      "Not-supported deviation.";
    deviate not-supported;
  }

  deviation "/oc-netinst:network-instances/oc-netinst:network-instance/oc-netinst:afts/oc-netinst:ethernet" {
    description
      "Not-supported deviation.";
    deviate not-supported;
  }

  deviation "/oc-netinst:network-instances/oc-netinst:network-instance/oc-netinst:afts/oc-netinst:policy-forwarding" {
    description
      "Not-supported deviation.";
    deviate not-supported;
  }

  deviation "/oc-netinst:network-instances/oc-netinst:network-instance/oc-netinst:afts/oc-netinst:ipv4-unicast/oc-netinst:ipv4-entry/oc-netinst:state/oc-aftni:origin-network-instance" {
    description
      "Not-supported deviation.";
    deviate not-supported;
  }

  deviation "/oc-netinst:network-instances/oc-netinst:network-instance/oc-netinst:afts/oc-netinst:ipv4-unicast/oc-netinst:ipv4-entry/oc-netinst:state/oc-netinst:decapsulate-header" {
    description
      "Not-supported deviation.";
    deviate not-supported;
  }

  deviation "/oc-netinst:network-instances/oc-netinst:network-instance/oc-netinst:afts/oc-netinst:ipv4-unicast/oc-netinst:ipv4-entry/oc-netinst:state/oc-netinst:entry-metadata" {
    description
      "Not-supported deviation.";
    deviate not-supported;
  }

  deviation "/oc-netinst:network-instances/oc-netinst:network-instance/oc-netinst:afts/oc-netinst:ipv6-unicast/oc-netinst:ipv6-entry/oc-netinst:state/oc-aftni:origin-network-instance" {
    description
      "Not-supported deviation.";
    deviate not-supported;
  }

  deviation "/oc-netinst:network-instances/oc-netinst:network-instance/oc-netinst:afts/oc-netinst:ipv6-unicast/oc-netinst:ipv6-entry/oc-netinst:state/oc-netinst:counters" {
    description
      "Not-supported deviation.";
    deviate not-supported;
  }

  deviation "/oc-netinst:network-instances/oc-netinst:network-instance/oc-netinst:afts/oc-netinst:ipv6-unicast/oc-netinst:ipv6-entry/oc-netinst:state/oc-netinst:decapsulate-header" {
    description
      "Not-supported deviation.";
    deviate not-supported;
  }

  deviation "/oc-netinst:network-instances/oc-netinst:network-instance/oc-netinst:afts/oc-netinst:ipv6-unicast/oc-netinst:ipv6-entry/oc-netinst:state/oc-netinst:entry-metadata" {
    description
      "Not-supported deviation.";
    deviate not-supported;
  }

  deviation "/oc-netinst:network-instances/oc-netinst:network-instance/oc-netinst:afts/oc-netinst:mpls/oc-netinst:label-entry/oc-netinst:state/oc-netinst:entry-metadata" {
    description
      "Not-supported deviation.";
    deviate not-supported;
  }

  deviation "/oc-netinst:network-instances/oc-netinst:network-instance/oc-netinst:afts/oc-netinst:mpls/oc-netinst:label-entry/oc-netinst:state/oc-netinst:popped-mpls-label-stack" {
    description
      "Not-supported deviation.";
    deviate not-supported;
  }

  deviation "/oc-netinst:network-instances/oc-netinst:network-instance/oc-netinst:afts/oc-netinst:next-hop-groups/oc-netinst:next-hop-group/oc-netinst:conditional" {
    description
      "Not-supported deviation.";
    deviate not-supported;
  }

  deviation "/oc-netinst:network-instances/oc-netinst:network-instance/oc-netinst:afts/oc-netinst:next-hop-groups/oc-netinst:next-hop-group/oc-netinst:state/oc-netinst:backup-active" {
    description
      "Not-supported deviation.";
    deviate not-supported;
  }

  deviation "/oc-netinst:network-instances/oc-netinst:network-instance/oc-netinst:afts/oc-netinst:next-hop-groups/oc-netinst:next-hop-group/oc-netinst:state/oc-netinst:backup-next-hop-group" {
    description
      "Not-supported deviation.";
    deviate not-supported;
  }

  deviation "/oc-netinst:network-instances/oc-netinst:network-instance/oc-netinst:afts/oc-netinst:next-hop-groups/oc-netinst:next-hop-group/oc-netinst:state/oc-netinst:color" {
    description
      "Not-supported deviation.";
    deviate not-supported;
  }

  deviation "/oc-netinst:network-instances/oc-netinst:network-instance/oc-netinst:afts/oc-netinst:next-hops/oc-netinst:next-hop/oc-netinst:encap-headers" {
    description
      "Not-supported deviation.";
    deviate not-supported;
  }

  deviation "/oc-netinst:network-instances/oc-netinst:network-instance/oc-netinst:afts/oc-netinst:next-hops/oc-netinst:next-hop/oc-netinst:state/oc-aftni:network-instance" {
    description
      "Not-supported deviation.";
    deviate not-supported;
  }

  deviation "/oc-netinst:network-instances/oc-netinst:network-instance/oc-netinst:afts/oc-netinst:next-hops/oc-netinst:next-hop/oc-netinst:state/oc-netinst:decapsulate-header" {
    description
      "Not-supported deviation.";
    deviate not-supported;
  }

  deviation "/oc-netinst:network-instances/oc-netinst:network-instance/oc-netinst:afts/oc-netinst:next-hops/oc-netinst:next-hop/oc-netinst:state/oc-netinst:lsp-name" {
    description
      "Not-supported deviation.";
    deviate not-supported;
  }

  deviation "/oc-netinst:network-instances/oc-netinst:network-instance/oc-netinst:afts/oc-netinst:next-hops/oc-netinst:next-hop/oc-netinst:state/oc-netinst:origin-protocol" {
    description
      "Not-supported deviation.";
    deviate not-supported;
  }

  deviation "/oc-netinst:network-instances/oc-netinst:network-instance/oc-netinst:afts/oc-netinst:next-hops/oc-netinst:next-hop/oc-netinst:state/oc-netinst:programmed-index" {
    description
      "Not-supported deviation.";
    deviate not-supported;
  }

  deviation "/oc-netinst:network-instances/oc-netinst:network-instance/oc-netinst:afts/oc-netinst:next-hops/oc-netinst:next-hop/oc-netinst:state/oc-netinst:tunnel-src-ip-address" {
    description
      "Not-supported deviation.";
    deviate not-supported;
  }

  deviation "/oc-netinst:network-instances/oc-netinst:network-instance/oc-netinst:afts/oc-netinst:next-hops/oc-netinst:next-hop/oc-netinst:state/oc-netinst:vni-label" {
    description
      "Not-supported deviation.";
    deviate not-supported;
  }

  deviation "/oc-netinst:network-instances/oc-netinst:network-instance/oc-netinst:config/oc-netinst:fallback-network-instance" {
    description
      "Not-supported deviation.";
    deviate not-supported;
  }

  deviation "/oc-netinst:network-instances/oc-netinst:network-instance/oc-netinst:config/oc-netinst:router-id" {
    description
      "Not-supported deviation.";
    deviate not-supported;
  }

  deviation "/oc-netinst:network-instances/oc-netinst:network-instance/oc-netinst:fdb/oc-netinst:arp-proxy" {
    description
      "Not-supported deviation.";
    deviate not-supported;
  }

  deviation "/oc-netinst:network-instances/oc-netinst:network-instance/oc-netinst:fdb/oc-netinst:config" {
    description
      "Not-supported deviation.";
    deviate not-supported;
  }

  deviation "/oc-netinst:network-instances/oc-netinst:network-instance/oc-netinst:fdb/oc-netinst:l2rib" {
    description
      "Not-supported deviation.";
    deviate not-supported;
  }

  deviation "/oc-netinst:network-instances/oc-netinst:network-instance/oc-netinst:fdb/oc-netinst:mac-mobility" {
    description
      "Not-supported deviation.";
    deviate not-supported;
  }

  deviation "/oc-netinst:network-instances/oc-netinst:network-instance/oc-netinst:fdb/oc-netinst:nd-proxy" {
    description
      "Not-supported deviation.";
    deviate not-supported;
  }

  deviation "/oc-netinst:network-instances/oc-netinst:network-instance/oc-netinst:fdb/oc-netinst:state" {
    description
      "Not-supported deviation.";
    deviate not-supported;
  }

  deviation "/oc-netinst:network-instances/oc-netinst:network-instance/oc-netinst:fdb/oc-netinst:mac-table/oc-netinst:entries/oc-netinst:entry/oc-netinst:interface/oc-netinst:interface-ref/oc-netinst:config" {
    description
      "Not-supported deviation.";
    deviate not-supported;
  }

  deviation "/oc-netinst:network-instances/oc-netinst:network-instance/oc-netinst:fdb/oc-netinst:mac-table/oc-netinst:entries/oc-netinst:entry/oc-netinst:state/oc-netinst:age" {
    description
      "Not-supported deviation.";
    deviate not-supported;
  }

  deviation "/oc-netinst:network-instances/oc-netinst:network-instance/oc-netinst:fdb/oc-netinst:mac-table/oc-netinst:entries/oc-netinst:entry/oc-netinst:state/oc-netinst:evi" {
    description
      "Not-supported deviation.";
    deviate not-supported;
  }

  deviation "/oc-netinst:network-instances/oc-netinst:network-instance/oc-netinst:inter-instance-policies/oc-netinst:import-export-policy" {
    description
      "Not-supported deviation.";
    deviate not-supported;
  }

  deviation "/oc-netinst:network-instances/oc-netinst:network-instance/oc-netinst:inter-instance-policies/oc-netinst:apply-policy/oc-netinst:state" {
    description
      "Not-supported deviation.";
    deviate not-supported;
  }

  deviation "/oc-netinst:network-instances/oc-netinst:network-instance/oc-netinst:inter-instance-policies/oc-netinst:apply-policy/oc-netinst:config/oc-netinst:default-export-policy" {
    description
      "Not-supported deviation.";
    deviate not-supported;
  }

  deviation "/oc-netinst:network-instances/oc-netinst:network-instance/oc-netinst:inter-instance-policies/oc-netinst:apply-policy/oc-netinst:config/oc-netinst:export-policy" {
    description
      "Not-supported deviation.";
    deviate not-supported;
  }

  deviation "/oc-netinst:network-instances/oc-netinst:network-instance/oc-netinst:inter-instance-policies/oc-netinst:apply-policy/oc-netinst:config/oc-netinst:import-policy" {
    description
      "Not-supported deviation.";
    deviate not-supported;
  }

  deviation "/oc-netinst:network-instances/oc-netinst:network-instance/oc-netinst:interfaces/oc-netinst:interface/oc-netinst:config/oc-netinst:associated-address-families" {
    description
      "Not-supported deviation.";
    deviate not-supported;
  }

  deviation "/oc-netinst:network-instances/oc-netinst:network-instance/oc-netinst:interfaces/oc-netinst:interface/oc-netinst:config/oc-netinst:irb-anycast-gateway" {
    description
      "Not-supported deviation.";
    deviate not-supported;
  }

  deviation "/oc-netinst:network-instances/oc-netinst:network-instance/oc-netinst:interfaces/oc-netinst:interface/oc-netinst:config/oc-netinst:mac-pinning" {
    description
      "Not-supported deviation.";
    deviate not-supported;
  }

  deviation "/oc-netinst:network-instances/oc-netinst:network-instance/oc-netinst:interfaces/oc-netinst:interface/oc-netinst:state/oc-netinst:associated-address-families" {
    description
      "Not-supported deviation.";
    deviate not-supported;
  }

  deviation "/oc-netinst:network-instances/oc-netinst:network-instance/oc-netinst:interfaces/oc-netinst:interface/oc-netinst:state/oc-netinst:irb-anycast-gateway" {
    description
      "Not-supported deviation.";
    deviate not-supported;
  }

  deviation "/oc-netinst:network-instances/oc-netinst:network-instance/oc-netinst:interfaces/oc-netinst:interface/oc-netinst:state/oc-netinst:mac-pinning" {
    description
      "Not-supported deviation.";
    deviate not-supported;
  }

  deviation "/oc-netinst:network-instances/oc-netinst:network-instance/oc-netinst:mpls/oc-netinst:global/oc-netinst:config/oc-netinst:null-label" {
    description
      "Not-supported deviation.";
    deviate not-supported;
  }

  deviation "/oc-netinst:network-instances/oc-netinst:network-instance/oc-netinst:mpls/oc-netinst:global/oc-netinst:config/oc-netinst:pw-encapsulation" {
    description
      "Not-supported deviation.";
    deviate not-supported;
  }

  deviation "/oc-netinst:network-instances/oc-netinst:network-instance/oc-netinst:mpls/oc-netinst:global/oc-netinst:config/oc-netinst:ttl-propagation" {
    description
      "Not-supported deviation.";
    deviate not-supported;
  }

  deviation "/oc-netinst:network-instances/oc-netinst:network-instance/oc-netinst:mpls/oc-netinst:global/oc-netinst:state/oc-netinst:null-label" {
    description
      "Not-supported deviation.";
    deviate not-supported;
  }

  deviation "/oc-netinst:network-instances/oc-netinst:network-instance/oc-netinst:mpls/oc-netinst:global/oc-netinst:state/oc-netinst:pw-encapsulation" {
    description
      "Not-supported deviation.";
    deviate not-supported;
  }

  deviation "/oc-netinst:network-instances/oc-netinst:network-instance/oc-netinst:mpls/oc-netinst:global/oc-netinst:state/oc-netinst:ttl-propagation" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:config" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:state" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:config/oc-netinst:index" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:config/oc-netinst:interface" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:config/oc-netinst:ip-address" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:config/oc-netinst:push-label" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:config/oc-netinst:subinterface" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:state/oc-netinst:index" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:state/oc-netinst:interface" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:state/oc-netinst:ip-address" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:state/oc-netinst:push-label" {
    description
      "Not-supported deviation.";
    deviate not-supported;
  }

  deviation "/oc-netinst:network-instances/oc-netinst:network-instance/oc-netinst:mpls/oc-netinst:lsps/oc-netinst:static-lsps/oc-netinst:static-lsp/oc-netinst:egress/oc-netinst:lsp-next-hops/oc-netinst:lsp-next-hop/oc-netinst:state/oc-netinst:subinterface" {
    description
      "Not-supported deviation.";
    deviate not-supported;
  }

  deviation "/oc-netinst:network-instances/oc-netinst:network-instance/oc-netinst:mpls/oc-netinst:lsps/oc-netinst:static-lsps/oc-netinst:static-lsp/oc-netinst:transit/oc-netinst:config" {
    description
      "Not-supported deviation.";
    deviate not-supported;
  }

  deviation "/oc-netinst:network-instances/oc-netinst:network-instance/oc-netinst:mpls/oc-netinst:lsps/oc-netinst:static-lsps/oc-netinst:static-lsp/oc-netinst:transit/oc-netinst:state" {
    description
      "Not-supported deviation.";
    deviate not-supported;
  }

  deviation "/oc-netinst:network-instances/oc-netinst:network-instance/oc-netinst:mpls/oc-netinst:lsps/oc-netinst:static-lsps/oc-netinst:static-lsp/oc-netinst:transit/oc-netinst:lsp-next-hops/oc-netinst:lsp-next-hop" {
    description
      "Not-supported deviation.";
    deviate not-supported;
  }

  deviation "/oc-netinst:network-instances/oc-netinst:network-instance/oc-netinst:mpls/oc-netinst:te-global-attributes/oc-netinst:te-lsp-timers" {
    description
      "Not-supported deviation.";
    deviate not-supported;
  }

  deviation "/oc-netinst:network-instances/oc-netinst:network-instance/oc-netinst:mpls/oc-netinst:te-global-attributes/oc-netinst:srlgs/oc-netinst:srlg/oc-netinst:static-srlg-members" {
    description
      "Not-supported deviation.";
    deviate not-supported;
  }

  deviation "/oc-netinst:network-instances/oc-netinst:network-instance/oc-netinst:mpls/oc-netinst:te-global-attributes/oc-netinst:srlgs/oc-netinst:srlg/oc-netinst:config/oc-netinst:cost" {
    description
      "Not-supported deviation.";
    deviate not-supported;
  }

  deviation "/oc-netinst:network-instances/oc-netinst:network-instance/oc-netinst:mpls/oc-netinst:te-global-attributes/oc-netinst:srlgs/oc-netinst:srlg/oc-netinst:config/oc-netinst:flooding-type" {
    description
      "Not-supported deviation.";
    deviate not-supported;
  }

  deviation "/oc-netinst:network-instances/oc-netinst:network-instance/oc-netinst:mpls/oc-netinst:te-global-attributes/oc-netinst:srlgs/oc-netinst:srlg/oc-netinst:state/oc-netinst:cost" {
    description
      "Not-supported deviation.";
    deviate not-supported;
  }

  deviation "/oc-netinst:network-instances/oc-netinst:network-instance/oc-netinst:mpls/oc-netinst:te-global-attributes/oc-netinst:srlgs/oc-netinst:srlg/oc-netinst:state/oc-netinst:flooding-type" {
    description
      "Not-supported deviation.";
    deviate not-supported;
  }

  deviation "/oc-netinst:network-instances/oc-netinst:network-instance/oc-netinst:policy-forwarding/oc-netinst:path-selection-groups" {
    description
      "Not-supported deviation.";
    deviate not-supported;
  }

  deviation "/oc-netinst:network-instances/oc-netinst:network-instance/oc-netinst:policy-forwarding/oc-netinst:interfaces/oc-netinst:interface/oc-netinst:config/oc-netinst:apply-forwarding-policy" {
    description
      "Not-supported deviation.";
    deviate not-supported;
  }

  deviation "/oc-netinst:network-instances/oc-netinst:network-instance/oc-netinst:policy-forwarding/oc-netinst:interfaces/oc-netinst:interface/oc-netinst:state/oc-netinst:apply-forwarding-policy" {
    description
      "Not-supported deviation.";
    deviate not-supported;
  }

  deviation "/oc-netinst:network-instances/oc-netinst:network-instance/oc-netinst:policy-forwarding/oc-netinst:policies/oc-netinst:policy/oc-netinst:rules/oc-netinst:rule/oc-netinst:l2" {
    description
      "Not-supported deviation.";
    deviate not-supported;
  }

  deviation "/oc-netinst:network-instances/oc-netinst:network-instance/oc-netinst:policy-forwarding/oc-netinst:policies/oc-netinst:policy/oc-netinst:rules/oc-netinst:rule/oc-netinst:transport" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:encapsulate-gre" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:config/oc-netinst:decapsulate-gre" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:config/oc-netinst:decapsulate-gue" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:config/oc-netinst:decapsulate-mpls-in-udp" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:config/oc-netinst:discard" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:config/oc-netinst:next-hop" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:config/oc-netinst:path-selection-group" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:state/oc-netinst:decapsulate-gre" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:state/oc-netinst:decapsulate-gue" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:state/oc-netinst:decapsulate-mpls-in-udp" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:state/oc-netinst:discard" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:state/oc-netinst:next-hop" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-netinst:state/oc-netinst:path-selection-group" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-pf-srte:segment-lists/oc-pf-srte:segment-list/oc-pf-srte:sids/oc-pf-srte:sid/oc-pf-srte:config/oc-pf-srte:mpls-tc" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-pf-srte:segment-lists/oc-pf-srte:segment-list/oc-pf-srte:sids/oc-pf-srte:sid/oc-pf-srte:config/oc-pf-srte:mpls-ttl" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-pf-srte:segment-lists/oc-pf-srte:segment-list/oc-pf-srte:sids/oc-pf-srte:sid/oc-pf-srte:state/oc-pf-srte:mpls-tc" {
    description
      "Not-supported deviation.";
    deviate not-supported;
  }

  deviation "/oc-netinst:network-instances/oc-netinst:network-instance/oc-netinst:policy-forwarding/oc-netinst:policies/oc-netinst:policy/oc-netinst:rules/oc-netinst:rule/oc-netinst:action/oc-pf-srte:segment-lists/oc-pf-srte:segment-list/oc-pf-srte:sids/oc-pf-srte:sid/oc-pf-srte:state/oc-pf-srte:mpls-ttl" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:icmpv4" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:config/oc-netinst:destination-address" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:config/oc-netinst:destination-address-prefix-set" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:config/oc-netinst:dscp" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:config/oc-netinst:hop-limit" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:config/oc-netinst:length" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:config/oc-netinst:source-address-prefix-set" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:state/oc-netinst:destination-address" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:state/oc-netinst:destination-address-prefix-set" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:state/oc-netinst:dscp" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:state/oc-netinst:hop-limit" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:state/oc-netinst:length" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv4/oc-netinst:state/oc-netinst:source-address-prefix-set" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:icmpv6" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:config/oc-netinst:destination-address" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:config/oc-netinst:destination-address-prefix-set" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:config/oc-netinst:destination-flow-label" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:config/oc-netinst:dscp" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:config/oc-netinst:hop-limit" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:config/oc-netinst:length" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:config/oc-netinst:protocol" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:config/oc-netinst:source-address-prefix-set" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:config/oc-netinst:source-flow-label" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:state/oc-netinst:destination-address" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:state/oc-netinst:destination-address-prefix-set" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:state/oc-netinst:destination-flow-label" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:state/oc-netinst:dscp" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:state/oc-netinst:hop-limit" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:state/oc-netinst:length" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:state/oc-netinst:protocol" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:state/oc-netinst:source-address-prefix-set" {
    description
      "Not-supported deviation.";
    deviate not-supported;
  }

  deviation "/oc-netinst:network-instances/oc-netinst:network-instance/oc-netinst:policy-forwarding/oc-netinst:policies/oc-netinst:policy/oc-netinst:rules/oc-netinst:rule/oc-netinst:ipv6/oc-netinst:state/oc-netinst:source-flow-label" {
    description
      "Not-supported deviation.";
    deviate not-supported;
  }

  deviation "/oc-netinst:network-instances/oc-netinst:network-instance/oc-netinst:policy-forwarding/oc-netinst:policies/oc-netinst:policy/oc-netinst:rules/oc-netinst:rule/oc-netinst:state/oc-netinst:matched-octets" {
    description
      "Not-supported deviation.";
    deviate not-supported;
  }

  deviation "/oc-netinst:network-instances/oc-netinst:network-instance/oc-netinst:policy-forwarding/oc-netinst:policies/oc-netinst:policy/oc-netinst:rules/oc-netinst:rule/oc-netinst:state/oc-netinst:matched-pkts" {
    description
      "Not-supported deviation.";
    deviate not-supported;
  }

  deviation "/oc-netinst:network-instances/oc-netinst:network-instance/oc-netinst:protocols/oc-netinst:protocol/oc-netinst:igmp" {
    description
      "Not-supported deviation.";
    deviate not-supported;
  }

  deviation "/oc-netinst:network-instances/oc-netinst:network-instance/oc-netinst:protocols/oc-netinst:protocol/oc-netinst:local-aggregates" {
    description
      "Not-supported deviation.";
    deviate not-supported;
  }

  deviation "/oc-netinst:network-instances/oc-netinst:network-instance/oc-netinst:protocols/oc-netinst:protocol/oc-netinst:pcep" {
    description
      "Not-supported deviation.";
    deviate not-supported;
  }

  deviation "/oc-netinst:network-instances/oc-netinst:network-instance/oc-netinst:protocols/oc-netinst:protocol/oc-netinst:bgp/oc-netinst:global/oc-netinst:apply-policy" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:apply-policy" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:graceful-restart" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:ipv4-labeled-unicast" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:ipv4-unicast" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:ipv6-labeled-unicast" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:ipv6-unicast" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:l2vpn-evpn" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:l2vpn-vpls" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:l3vpn-ipv4-multicast" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:l3vpn-ipv6-multicast" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:route-selection-options" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:srte-policy-ipv4" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:srte-policy-ipv6" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:add-paths/oc-netinst:config/oc-netinst:eligible-prefix-policy" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:add-paths/oc-netinst:config/oc-netinst:receive" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:add-paths/oc-netinst:config/oc-netinst:send" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:add-paths/oc-netinst:config/oc-netinst:send-max" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:add-paths/oc-netinst:state/oc-netinst:eligible-prefix-policy" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:add-paths/oc-netinst:state/oc-netinst:receive" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:add-paths/oc-netinst:state/oc-netinst:send" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:add-paths/oc-netinst:state/oc-netinst:send-max" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:config/oc-netinst:send-community-type" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:l3vpn-ipv4-unicast/oc-netinst:prefix-limit-received" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:l3vpn-ipv6-unicast/oc-netinst:prefix-limit-received" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:state/oc-netinst:send-community-type" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:state/oc-netinst:total-paths" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:use-multiple-paths/oc-netinst:config" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:use-multiple-paths/oc-netinst:ibgp" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:use-multiple-paths/oc-netinst:state" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:use-multiple-paths/oc-netinst:ebgp/oc-netinst:config/oc-netinst:allow-multiple-as" {
    description
      "Not-supported deviation.";
    deviate not-supported;
  }

  deviation "/oc-netinst:network-instances/oc-netinst:network-instance/oc-netinst:protocols/oc-netinst:protocol/oc-netinst:bgp/oc-netinst:global/oc-netinst:afi-safis/oc-netinst:afi-safi/oc-netinst:use-multiple-paths/oc-netinst:ebgp/oc-netinst:state/oc-netinst:allow-multiple-as" {
    description
      "Not-supported deviation.";
    deviate not-supported;
  }

  deviation "/oc-netinst:network-instances/oc-netinst:network-instance/oc-netinst:protocols/oc-netinst:protocol/oc-netinst:bgp/oc-netinst:global/oc-netinst:state/oc-netinst:total-paths" {
    description
      "Not-supported deviation.";
    deviate not-supported;
  }

  deviation "/oc-netinst:network-instances/oc-netinst:network-instance/oc-netinst:protocols/oc-netinst:protocol/oc-netinst:bgp/oc-netinst:global/oc-netinst:use-multiple-paths/oc-netinst:ebgp/oc-netinst:link-bandwidth-ext-community" {
    description
      "Not-supported deviation.";
    deviate not-supported;
  }

  deviation "/oc-netinst:network-instances/oc-netinst:network-instance/oc-netinst:protocols/oc-netinst:protocol/oc-netinst:bgp/oc-netinst:global/oc-netinst:use-multiple-paths/oc-netinst:ibgp/oc-netinst:link-bandwidth-ext-community" {
    description
      "Not-supported deviation.";
    deviate not-supported;
  }

  deviation "/oc-netinst:network-instances/oc-netinst:network-instance/oc-netinst:protocols/oc-netinst:protocol/oc-netinst:bgp/oc-netinst:global/oc-netinst:use-multiple-paths/oc-netinst:ibgp/oc-netinst:state" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:error-handling" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:use-multiple-paths" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:ipv4-labeled-unicast" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:ipv6-labeled-unicast" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:l2vpn-vpls" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-multicast" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:l3vpn-ipv4-unicast" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-multicast" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:l3vpn-ipv6-unicast" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:srte-policy-ipv4" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:srte-policy-ipv6" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:config/oc-netinst:eligible-prefix-policy" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:state/oc-netinst:eligible-prefix-policy" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:config/oc-netinst:send-community-type" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:prevent-teardown" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:prevent-teardown" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:prevent-teardown" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:prevent-teardown" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit-received" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:afi-safis/oc-netinst:afi-safi/oc-netinst:state/oc-netinst:send-community-type" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:graceful-restart/oc-netinst:config/oc-netinst:restart-time" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:graceful-restart/oc-netinst:config/oc-netinst:stale-routes-time" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:graceful-restart/oc-netinst:state/oc-netinst:local-restarting" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:graceful-restart/oc-netinst:state/oc-netinst:mode" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:graceful-restart/oc-netinst:state/oc-netinst:peer-restarting" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:graceful-restart/oc-netinst:state/oc-netinst:restart-time" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:graceful-restart/oc-netinst:state/oc-netinst:stale-routes-time" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:route-reflector/oc-netinst:state/oc-netinst:route-reflector-cluster-id" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:state/oc-netinst:send-community-type" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:transport/oc-netinst:config/oc-netinst:tcp-mss" {
    description
      "Not-supported deviation.";
    deviate not-supported;
  }

  deviation "/oc-netinst:network-instances/oc-netinst:network-instance/oc-netinst:protocols/oc-netinst:protocol/oc-netinst:bgp/oc-netinst:neighbors/oc-netinst:neighbor/oc-netinst:transport/oc-netinst:state/oc-netinst:tcp-mss" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:error-handling" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:use-multiple-paths" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv4-labeled-unicast" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv6-labeled-unicast" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:l2vpn-vpls" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-multicast" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:l3vpn-ipv4-unicast" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-multicast" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:l3vpn-ipv6-unicast" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:srte-policy-ipv4" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:srte-policy-ipv6" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:config/oc-netinst:eligible-prefix-policy" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:state/oc-netinst:eligible-prefix-policy" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:config/oc-netinst:send-community-type" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:prevent-teardown" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:prefix-limit-exceeded" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:prevent-teardown" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit-received/oc-netinst:state/oc-netinst:prefix-limit-exceeded" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:prevent-teardown" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:prefix-limit-exceeded" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:prevent-teardown" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit-received/oc-netinst:state/oc-netinst:prefix-limit-exceeded" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit-received" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:state/oc-netinst:send-community-type" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:ebgp" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:afi-safis/oc-netinst:afi-safi/oc-netinst:use-multiple-paths/oc-netinst:ibgp" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:config/oc-netinst:route-flap-damping" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:graceful-restart/oc-netinst:config/oc-netinst:restart-time" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:graceful-restart/oc-netinst:config/oc-netinst:stale-routes-time" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:graceful-restart/oc-netinst:state/oc-netinst:restart-time" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:graceful-restart/oc-netinst:state/oc-netinst:stale-routes-time" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:route-reflector/oc-netinst:state/oc-netinst:route-reflector-cluster-id" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:state/oc-netinst:peer-type" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:state/oc-netinst:route-flap-damping" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:state/oc-netinst:total-paths" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:state/oc-netinst:total-prefixes" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:transport/oc-netinst:config/oc-netinst:tcp-mss" {
    description
      "Not-supported deviation.";
    deviate not-supported;
  }

  deviation "/oc-netinst:network-instances/oc-netinst:network-instance/oc-netinst:protocols/oc-netinst:protocol/oc-netinst:bgp/oc-netinst:peer-groups/oc-netinst:peer-group/oc-netinst:transport/oc-netinst:state/oc-netinst:tcp-mss" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv4-srte-policy" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv6-srte-policy" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:l2vpn-evpn" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv4-unicast/oc-netinst:neighbors" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv4-unicast/oc-netinst:loc-rib/oc-netinst:state" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv4-unicast/oc-netinst:loc-rib/oc-netinst:routes/oc-netinst:route/oc-netinst:unknown-attributes" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv4-unicast/oc-netinst:loc-rib/oc-netinst:routes/oc-netinst:route/oc-netinst:state/oc-netinst:invalid-reason" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv6-unicast/oc-netinst:neighbors" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv6-unicast/oc-netinst:loc-rib/oc-netinst:state" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv6-unicast/oc-netinst:loc-rib/oc-netinst:routes/oc-netinst:route/oc-netinst:unknown-attributes" {
    description
      "Not-supported deviation.";
    deviate not-supported;
  }

  deviation "/oc-netinst:network-instances/oc-netinst:network-instance/oc-netinst:protocols/oc-netinst:protocol/oc-netinst:bgp/oc-netinst:rib/oc-netinst:afi-safis/oc-netinst:afi-safi/oc-netinst:ipv6-unicast/oc-netinst:loc-rib/oc-netinst:routes/oc-netinst:route/oc-netinst:state/oc-netinst:invalid-reason" {
    description
      "Not-supported deviation.";
    deviate not-supported;
  }

  deviation "/oc-netinst:network-instances/oc-netinst:network-instance/oc-netinst:protocols/oc-netinst:protocol/oc-netinst:bgp/oc-netinst:rib/oc-netinst:attr-sets/oc-netinst:attr-set/oc-netinst:tunnel-encapsulation" {
    description
      "Not-supported deviation.";
    deviate not-supported;
  }

  deviation "/oc-netinst:network-instances/oc-netinst:network-instance/oc-netinst:protocols/oc-netinst:protocol/oc-netinst:isis/oc-netinst:global/oc-netinst:inter-level-propagation-policies" {
    description
      "Not-supported deviation.";
    deviate not-supported;
  }

  deviation "/oc-netinst:network-instances/oc-netinst:network-instance/oc-netinst:protocols/oc-netinst:protocol/oc-netinst:isis/oc-netinst:global/oc-netinst:afi-safi/oc-netinst:af/oc-netinst:multi-topology/oc-netinst:config/oc-netinst:afi-name" {
    description
      "Not-supported deviation.";
    deviate not-supported;
  }

  deviation "/oc-netinst:network-instances/oc-netinst:network-instance/oc-netinst:protocols/oc-netinst:protocol/oc-netinst:isis/oc-netinst:global/oc-netinst:afi-safi/oc-netinst:af/oc-netinst:multi-topology/oc-netinst:config/oc-netinst:safi-name" {
    description
      "Not-supported deviation.";
    deviate not-supported;
  }

  deviation "/oc-netinst:network-instances/oc-netinst:network-instance/oc-netinst:protocols/oc-netinst:protocol/oc-netinst:isis/oc-netinst:global/oc-netinst:afi-safi/oc-netinst:af/oc-netinst:multi-topology/oc-netinst:state/oc-netinst:afi-name" {
    description
      "Not-supported deviation.";
    deviate not-supported;
  }

  deviation "/oc-netinst:network-instances/oc-netinst:network-instance/oc-netinst:protocols/oc-netinst:protocol/oc-netinst:isis/oc-netinst:global/oc-netinst:afi-safi/oc-netinst:af/oc-netinst:multi-topology/oc-netinst:state/oc-netinst:safi-name" {
    description
      "Not-supported deviation.";
    deviate not-supported;
  }

  deviation "/oc-netinst:network-instances/oc-netinst:network-instance/oc-netinst:protocols/oc-netinst:protocol/oc-netinst:isis/oc-netinst:global/oc-netinst:config/oc-netinst:weighted-ecmp" {
    description
      "Not-supported deviation.";
    deviate not-supported;
  }

  deviation "/oc-netinst:network-instances/oc-netinst:network-instance/oc-netinst:protocols/oc-netinst:protocol/oc-netinst:isis/oc-netinst:global/oc-netinst:graceful-restart/oc-netinst:config/oc-netinst:interface-time-expirations" {
    description
      "Not-supported deviation.";
    deviate not-supported;
  }

  deviation "/oc-netinst:network-instances/oc-netinst:network-instance/oc-netinst:protocols/oc-netinst:protocol/oc-netinst:isis/oc-netinst:global/oc-netinst:graceful-restart/oc-netinst:config/oc-netinst:interface-timer" {
    description
      "Not-supported deviation.";
    deviate not-supported;
  }

  deviation "/oc-netinst:network-instances/oc-netinst:network-instance/oc-netinst:protocols/oc-netinst:protocol/oc-netinst:isis/oc-netinst:global/oc-netinst:graceful-restart/oc-netinst:config/oc-netinst:non-planned-only" {
    description
      "Not-supported deviation.";
    deviate not-supported;
  }

  deviation "/oc-netinst:network-instances/oc-netinst:network-instance/oc-netinst:protocols/oc-netinst:protocol/oc-netinst:isis/oc-netinst:global/oc-netinst:graceful-restart/oc-netinst:state/oc-netinst:interface-time-expirations" {
    description
      "Not-supported deviation.";
    deviate not-supported;
  }

  deviation "/oc-netinst:network-instances/oc-netinst:network-instance/oc-netinst:protocols/oc-netinst:protocol/oc-netinst:isis/oc-netinst:global/oc-netinst:graceful-restart/oc-netinst:state/oc-netinst:interface-timer" {
    description
      "Not-supported deviation.";
    deviate not-supported;
  }

  deviation "/oc-netinst:network-instances/oc-netinst:network-instance/oc-netinst:protocols/oc-netinst:protocol/oc-netinst:isis/oc-netinst:global/oc-netinst:graceful-restart/oc-netinst:state/oc-netinst:non-planned-only" {
    description
      "Not-supported deviation.";
    deviate not-supported;
  }

  deviation "/oc-netinst:network-instances/oc-netinst:network-instance/oc-netinst:protocols/oc-netinst:protocol/oc-netinst:isis/oc-netinst:global/oc-netinst:lsp-bit/oc-netinst:attached-bit/oc-netinst:config/oc-netinst:suppress-bit" {
    description
      "Not-supported deviation.";
    deviate not-supported;
  }

  deviation "/oc-netinst:network-instances/oc-netinst:network-instance/oc-netinst:protocols/oc-netinst:protocol/oc-netinst:isis/oc-netinst:global/oc-netinst:lsp-bit/oc-netinst:attached-bit/oc-netinst:state/oc-netinst:suppress-bit" {
    description
      "Not-supported deviation.";
    deviate not-supported;
  }

  deviation "/oc-netinst:network-instances/oc-netinst:network-instance/oc-netinst:protocols/oc-netinst:protocol/oc-netinst:isis/oc-netinst:global/oc-netinst:mpls/oc-netinst:igp-ldp-sync/oc-netinst:state/oc-netinst:post-session-up-delay" {
    description
      "Not-supported deviation.";
    deviate not-supported;
  }

  deviation "/oc-netinst:network-instances/oc-netinst:network-instance/oc-netinst:protocols/oc-netinst:protocol/oc-netinst:isis/oc-netinst:global/oc-netinst:reference-bandwidth/oc-netinst:state" {
    description
      "Not-supported deviation.";
    deviate not-supported;
  }

  deviation "/oc-netinst:network-instances/oc-netinst:network-instance/oc-netinst:protocols/oc-netinst:protocol/oc-netinst:isis/oc-netinst:global/oc-netinst:segment-routing/flex-algo:fad-bindings" {
    description
      "Not-supported deviation.";
    deviate not-supported;
  }

  deviation "/oc-netinst:network-instances/oc-netinst:network-instance/oc-netinst:protocols/oc-netinst:protocol/oc-netinst:isis/oc-netinst:global/oc-netinst:segment-routing/oc-netinst:flex-algorithm-bindings/oc-netinst:flex-algorithm-binding/oc-netinst:config/oc-netinst:participate" {
    description
      "Not-supported deviation.";
    deviate not-supported;
  }

  deviation "/oc-netinst:network-instances/oc-netinst:network-instance/oc-netinst:protocols/oc-netinst:protocol/oc-netinst:isis/oc-netinst:global/oc-netinst:segment-routing/oc-netinst:flex-algorithm-bindings/oc-netinst:flex-algorithm-binding/oc-netinst:state/oc-netinst:participate" {
    description
      "Not-supported deviation.";
    deviate not-supported;
  }

  deviation "/oc-netinst:network-instances/oc-netinst:network-instance/oc-netinst:protocols/oc-netinst:protocol/oc-netinst:isis/oc-netinst:global/oc-netinst:state/oc-netinst:authentication-check" {
    description
      "Not-supported deviation.";
    deviate not-supported;
  }

  deviation "/oc-netinst:network-instances/oc-netinst:network-instance/oc-netinst:protocols/oc-netinst:protocol/oc-netinst:isis/oc-netinst:global/oc-netinst:state/oc-netinst:max-ecmp-paths" {
    description
      "Not-supported deviation.";
    deviate not-supported;
  }

  deviation "/oc-netinst:network-instances/oc-netinst:network-instance/oc-netinst:protocols/oc-netinst:protocol/oc-netinst:isis/oc-netinst:global/oc-netinst:state/oc-netinst:weighted-ecmp" {
    description
      "Not-supported deviation.";
    deviate not-supported;
  }

  deviation "/oc-netinst:network-instances/oc-netinst:network-instance/oc-netinst:protocols/oc-netinst:protocol/oc-netinst:isis/oc-netinst:global/oc-netinst:timers/oc-netinst:lsp-generation/oc-netinst:state/oc-netinst:adaptive-timer" {
    description
      "Not-supported deviation.";
    deviate not-supported;
  }

  deviation "/oc-netinst:network-instances/oc-netinst:network-instance/oc-netinst:protocols/oc-netinst:protocol/oc-netinst:isis/oc-netinst:global/oc-netinst:timers/oc-netinst:spf/oc-netinst:state/oc-netinst:adaptive-timer" {
    description
      "Not-supported deviation.";
    deviate not-supported;
  }

  deviation "/oc-netinst:network-instances/oc-netinst:network-instance/oc-netinst:protocols/oc-netinst:protocol/oc-netinst:isis/oc-netinst:interfaces/oc-netinst:interface/oc-netinst:authentication" {
    description
      "Not-supported deviation.";
    deviate not-supported;
  }

  deviation "/oc-netinst:network-instances/oc-netinst:network-instance/oc-netinst:protocols/oc-netinst:protocol/oc-netinst:isis/oc-netinst:interfaces/oc-netinst:interface/oc-netinst:enable-bfd" {
    description
      "Not-supported deviation.";
    deviate not-supported;
  }

  deviation "/oc-netinst:network-instances/oc-netinst:network-instance/oc-netinst:protocols/oc-netinst:protocol/oc-netinst:isis/oc-netinst:interfaces/oc-netinst:interface/oc-netinst:graceful-restart" {
    description
      "Not-supported deviation.";
    deviate not-supported;
  }

  deviation "/oc-netinst:network-instances/oc-netinst:network-instance/oc-netinst:protocols/oc-netinst:protocol/oc-netinst:isis/oc-netinst:interfaces/oc-netinst:interface/oc-netinst:mpls" {
    description
      "Not-supported deviation.";
    deviate not-supported;
  }

  deviation "/oc-netinst:network-instances/oc-netinst:network-instance/oc-netinst:protocols/oc-netinst:protocol/oc-netinst:isis/oc-netinst:interfaces/oc-netinst:interface/oc-netinst:weighted-ecmp" {
    description
      "Not-supported deviation.";
    deviate not-supported;
  }

  deviation "/oc-netinst:network-instances/oc-netinst:network-instance/oc-netinst:protocols/oc-netinst:protocol/oc-netinst:isis/oc-netinst:interfaces/oc-netinst:interface/oc-netinst:afi-safi/oc-netinst:af/oc-netinst:state" {
    description
      "Not-supported deviation.";
    deviate not-supported;
  }

  deviation "/oc-netinst:network-instances/oc-netinst:network-instance/oc-netinst:protocols/oc-netinst:protocol/oc-netinst:isis/oc-netinst:interfaces/oc-netinst:interface/oc-netinst:afi-safi/oc-netinst:af/oc-netinst:config/oc-netinst:afi-name" {
    description
      "Not-supported deviation.";
    deviate not-supported;
  }

  deviation "/oc-netinst:network-instances/oc-netinst:network-instance/oc-netinst:protocols/oc-netinst:protocol/oc-netinst:isis/oc-netinst:interfaces/oc-netinst:interface/oc-netinst:afi-safi/oc-netinst:af/oc-netinst:config/oc-netinst:safi-name" {
    description
      "Not-supported deviation.";
    deviate not-supported;
  }

  deviation "/oc-netinst:network-instances/oc-netinst:network-instance/oc-netinst:protocols/oc-netinst:protocol/oc-netinst:isis/oc-netinst:interfaces/oc-netinst:interface/oc-netinst:bfd/oc-netinst:state" {
    description
      "Not-supported deviation.";
    deviate not-supported;
  }

  deviation "/oc-netinst:network-instances/oc-netinst:network-instance/oc-netinst:protocols/oc-netinst:protocol/oc-netinst:isis/oc-netinst:interfaces/oc-netinst:interface/oc-netinst:circuit-counters/oc-netinst:state/oc-netinst:init-fails" {
    description
      "Not-supported deviation.";
    deviate not-supported;
  }

  deviation "/oc-netinst:network-instances/oc-netinst:network-instance/oc-netinst:protocols/oc-netinst:protocol/oc-netinst:isis/oc-netinst:interfaces/oc-netinst:interface/oc-netinst:levels/oc-netinst:level/oc-netinst:adjacencies/oc-netinst:adjacency/oc-netinst:state/oc-netinst:adjacency-type" {
    description
      "Not-supported deviation.";
    deviate not-supported;
  }

  deviation "/oc-netinst:network-instances/oc-netinst:network-instance/oc-netinst:protocols/oc-netinst:protocol/oc-netinst:isis/oc-netinst:interfaces/oc-netinst:interface/oc-netinst:levels/oc-netinst:level/oc-netinst:afi-safi/oc-netinst:af/oc-netinst:segment-routing/oc-netinst:adjacency-sids" {
    description
      "Not-supported deviation.";
    deviate not-supported;
  }

  deviation "/oc-netinst:network-instances/oc-netinst:network-instance/oc-netinst:protocols/oc-netinst:protocol/oc-netinst:isis/oc-netinst:interfaces/oc-netinst:interface/oc-netinst:levels/oc-netinst:level/oc-netinst:afi-safi/oc-netinst:af/oc-netinst:state/oc-netinst:enabled" {
    description
      "Not-supported deviation.";
    deviate not-supported;
  }

  deviation "/oc-netinst:network-instances/oc-netinst:network-instance/oc-netinst:protocols/oc-netinst:protocol/oc-netinst:isis/oc-netinst:interfaces/oc-netinst:interface/oc-netinst:levels/oc-netinst:level/oc-netinst:config/oc-netinst:passive" {
    description
      "Not-supported deviation.";
    deviate not-supported;
  }

  deviation "/oc-netinst:network-instances/oc-netinst:network-instance/oc-netinst:protocols/oc-netinst:protocol/oc-netinst:isis/oc-netinst:interfaces/oc-netinst:interface/oc-netinst:levels/oc-netinst:level/oc-netinst:hello-authentication/oc-netinst:config/oc-netinst:keychain" {
    description
      "Not-supported deviation.";
    deviate not-supported;
  }

  deviation "/oc-netinst:network-instances/oc-netinst:network-instance/oc-netinst:protocols/oc-netinst:protocol/oc-netinst:isis/oc-netinst:interfaces/oc-netinst:interface/oc-netinst:levels/oc-netinst:level/oc-netinst:hello-authentication/oc-netinst:state/oc-netinst:keychain" {
    description
      "Not-supported deviation.";
    deviate not-supported;
  }

  deviation "/oc-netinst:network-instances/oc-netinst:network-instance/oc-netinst:protocols/oc-netinst:protocol/oc-netinst:isis/oc-netinst:interfaces/oc-netinst:interface/oc-netinst:levels/oc-netinst:level/oc-netinst:state/oc-netinst:passive" {
    description
      "Not-supported deviation.";
    deviate not-supported;
  }

  deviation "/oc-netinst:network-instances/oc-netinst:network-instance/oc-netinst:protocols/oc-netinst:protocol/oc-netinst:isis/oc-netinst:interfaces/oc-netinst:interface/oc-netinst:timers/oc-netinst:state/oc-netinst:csnp-interval" {
    description
      "Not-supported deviation.";
    deviate not-supported;
  }

  deviation "/oc-netinst:network-instances/oc-netinst:network-instance/oc-netinst:protocols/oc-netinst:protocol/oc-netinst:isis/oc-netinst:levels/oc-netinst:level/oc-netinst:graceful-restart" {
    description
      "Not-supported deviation.";
    deviate not-supported;
  }

  deviation "/oc-netinst:network-instances/oc-netinst:network-instance/oc-netinst:protocols/oc-netinst:protocol/oc-netinst:isis/oc-netinst:levels/oc-netinst:level/oc-netinst:authentication/oc-netinst:config/oc-netinst:disable-csnp" {
    description
      "Not-supported deviation.";
    deviate not-supported;
  }

  deviation "/oc-netinst:network-instances/oc-netinst:network-instance/oc-netinst:protocols/oc-netinst:protocol/oc-netinst:isis/oc-netinst:levels/oc-netinst:level/oc-netinst:authentication/oc-netinst:config/oc-netinst:disable-lsp" {
    description
      "Not-supported deviation.";
    deviate not-supported;
  }

  deviation "/oc-netinst:network-instances/oc-netinst:network-instance/oc-netinst:protocols/oc-netinst:protocol/oc-netinst:isis/oc-netinst:levels/oc-netinst:level/oc-netinst:authentication/oc-netinst:config/oc-netinst:disable-psnp" {
    description
      "Not-supported deviation.";
    deviate not-supported;
  }

  deviation "/oc-netinst:network-instances/oc-netinst:network-instance/oc-netinst:protocols/oc-netinst:protocol/oc-netinst:isis/oc-netinst:levels/oc-netinst:level/oc-netinst:authentication/oc-netinst:config/oc-netinst:keychain" {
    description
      "Not-supported deviation.";
    deviate not-supported;
  }

  deviation "/oc-netinst:network-instances/oc-netinst:network-instance/oc-netinst:protocols/oc-netinst:protocol/oc-netinst:isis/oc-netinst:levels/oc-netinst:level/oc-netinst:authentication/oc-netinst:state/oc-netinst:disable-csnp" {
    description
      "Not-supported deviation.";
    deviate not-supported;
  }

  deviation "/oc-netinst:network-instances/oc-netinst:network-instance/oc-netinst:protocols/oc-netinst:protocol/oc-netinst:isis/oc-netinst:levels/oc-netinst:level/oc-netinst:authentication/oc-netinst:state/oc-netinst:disable-lsp" {
    description
      "Not-supported deviation.";
    deviate not-supported;
  }

  deviation "/oc-netinst:network-instances/oc-netinst:network-instance/oc-netinst:protocols/oc-netinst:protocol/oc-netinst:isis/oc-netinst:levels/oc-netinst:level/oc-netinst:authentication/oc-netinst:state/oc-netinst:disable-psnp" {
    description
      "Not-supported deviation.";
    deviate not-supported;
  }

  deviation "/oc-netinst:network-instances/oc-netinst:network-instance/oc-netinst:protocols/oc-netinst:protocol/oc-netinst:isis/oc-netinst:levels/oc-netinst:level/oc-netinst:authentication/oc-netinst:state/oc-netinst:keychain" {
    description
      "Not-supported deviation.";
    deviate not-supported;
  }

  deviation "/oc-netinst:network-instances/oc-netinst:network-instance/oc-netinst:protocols/oc-netinst:protocol/oc-netinst:isis/oc-netinst:levels/oc-netinst:level/oc-netinst:config/oc-netinst:enabled" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:undefined-tlvs" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:checksum" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:flags" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:id-length" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:is-type" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:maximum-area-addresses" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:pdu-length" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:pdu-type" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:remaining-lifetime" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:sequence-number" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:version" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:state/oc-netinst:version2" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:area-address" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:authentication" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:hostname" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:instance-ids" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-external-reachability" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv4-internal-reachability" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:is-alias-id" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:is-reachability" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:isis-neighbor-attribute" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:lsp-buffer-size" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv4-reachability" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-ipv6-reachability" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isis-neighbor-attribute" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:mt-isn" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:multi-topology" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:nlpid" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:purge-oi" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:undefined-subtlvs" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:flags" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:ipv4-source-router-id" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:ipv6-source-router-id" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:tag" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-ipv4-reachability/oc-netinst:prefixes/oc-netinst:prefix/oc-netinst:subtlvs/oc-netinst:subtlv/oc-netinst:tag64" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:undefined-subtlvs" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/flex-algo:application-specific-link-attributes" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:admin-group" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:available-bandwidth" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:bandwidth-constraints" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:extended-admin-group" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:ipv4-interface-address" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:ipv4-neighbor-address" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:ipv6-interface-address" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:ipv6-neighbor-address" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-attributes" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-delay" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-delay-variation" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-id" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-loss" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:link-protection-type" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:min-max-link-delay" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:residual-bandwidth" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:te-default-metric" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:unconstrained-lsp" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:extended-is-reachability/oc-netinst:neighbors/oc-netinst:neighbor/oc-netinst:instances/oc-netinst:instance/oc-netinst:subtlvs/oc-netinst:subtlv/oc-netinst:utilized-bandwidth" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:undefined-subtlvs" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:flags" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:ipv4-source-router-id" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:ipv6-source-router-id" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:tag" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:ipv6-reachability/oc-netinst:prefixes/oc-netinst:prefix/oc-netinst:subtlvs/oc-netinst:subtlv/oc-netinst:tag64" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:router-capabilities/oc-netinst:capability/oc-netinst:undefined-subtlvs" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:router-capabilities/oc-netinst:capability/oc-netinst:subtlvs/oc-netinst:subtlv/flex-algo:flexible-algorithm-definition" {
    description
      "Not-supported deviation.";
    deviate not-supported;
  }

  deviation "/oc-netinst:network-instances/oc-netinst:network-instance/oc-netinst:protocols/oc-netinst:protocol/oc-netinst:isis/oc-netinst:levels/oc-netinst:level/oc-netinst:link-state-database/oc-netinst:lsp/oc-netinst:tlvs/oc-netinst:tlv/oc-netinst:router-capabilities/oc-netinst:capability/oc-netinst:subtlvs/oc-netinst:subtlv/oc-netinst:segment-routing-algorithms" {
    description
      "Not-supported deviation.";
    deviate not-supported;
  }

  deviation "/oc-netinst:network-instances/oc-netinst:network-instance/oc-netinst:protocols/oc-netinst:protocol/oc-netinst:isis/oc-netinst:levels/oc-netinst:level/oc-netinst:state/oc-netinst:authentication-check" {
    description
      "Not-supported deviation.";
    deviate not-supported;
  }

  deviation "/oc-netinst:network-instances/oc-netinst:network-instance/oc-netinst:protocols/oc-netinst:protocol/oc-netinst:isis/oc-netinst:levels/oc-netinst:level/oc-netinst:system-level-counters/oc-netinst:state/oc-netinst:manual-address-drop-from-areas" {
    description
      "Not-supported deviation.";
    deviate not-supported;
  }

  deviation "/oc-netinst:network-instances/oc-netinst:network-instance/oc-netinst:protocols/oc-netinst:protocol/oc-netinst:isis/oc-netinst:levels/oc-netinst:level/oc-netinst:system-level-counters/oc-netinst:state/oc-netinst:part-changes" {
    description
      "Not-supported deviation.";
    deviate not-supported;
  }

  deviation "/oc-netinst:network-instances/oc-netinst:network-instance/oc-netinst:protocols/oc-netinst:protocol/oc-netinst:ospfv2/oc-netinst:areas/oc-netinst:area/oc-netinst:lsdb" {
    description
      "Not-supported deviation.";
    deviate not-supported;
  }

  deviation "/oc-netinst:network-instances/oc-netinst:network-instance/oc-netinst:protocols/oc-netinst:protocol/oc-netinst:ospfv2/oc-netinst:areas/oc-netinst:area/oc-netinst:mpls" {
    description
      "Not-supported deviation.";
    deviate not-supported;
  }

  deviation "/oc-netinst:network-instances/oc-netinst:network-instance/oc-netinst:protocols/oc-netinst:protocol/oc-netinst:ospfv2/oc-netinst:areas/oc-netinst:area/oc-netinst:state" {
    description
      "Not-supported deviation.";
    deviate not-supported;
  }

  deviation "/oc-netinst:network-instances/oc-netinst:network-instance/oc-netinst:protocols/oc-netinst:protocol/oc-netinst:ospfv2/oc-netinst:areas/oc-netinst:area/oc-netinst:virtual-links" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:interface-ref" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:lsa-filter" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:mpls" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:neighbors" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:state" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:config/oc-netinst:authentication-type" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:config/oc-netinst:hide-network" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:config/oc-netinst:multi-area-adjacency-primary" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:enable-bfd/oc-netinst:state" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:enable-bfd/oc-netinst:config/oc-netinst:desired-minimum-tx-interval" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:enable-bfd/oc-netinst:config/oc-netinst:detection-multiplier" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:enable-bfd/oc-netinst:config/oc-netinst:required-minimum-receive" {
    description
      "Not-supported deviation.";
    deviate not-supported;
  }

  deviation "/oc-netinst:network-instances/oc-netinst:network-instance/oc-netinst:protocols/oc-netinst:protocol/oc-netinst:ospfv2/oc-netinst:areas/oc-netinst:area/oc-netinst:interfaces/oc-netinst:interface/oc-netinst:timers/oc-netinst:state" {
    description
      "Not-supported deviation.";
    deviate not-supported;
  }

  deviation "/oc-netinst:network-instances/oc-netinst:network-instance/oc-netinst:protocols/oc-netinst:protocol/oc-netinst:ospfv2/oc-netinst:global/oc-netinst:inter-area-propagation-policies" {
    description
      "Not-supported deviation.";
    deviate not-supported;
  }

  deviation "/oc-netinst:network-instances/oc-netinst:network-instance/oc-netinst:protocols/oc-netinst:protocol/oc-netinst:ospfv2/oc-netinst:global/oc-netinst:mpls" {
    description
      "Not-supported deviation.";
    deviate not-supported;
  }

  deviation "/oc-netinst:network-instances/oc-netinst:network-instance/oc-netinst:protocols/oc-netinst:protocol/oc-netinst:ospfv2/oc-netinst:global/oc-netinst:state" {
    description
      "Not-supported deviation.";
    deviate not-supported;
  }

  deviation "/oc-netinst:network-instances/oc-netinst:network-instance/oc-netinst:protocols/oc-netinst:protocol/oc-netinst:ospfv2/oc-netinst:global/oc-netinst:config/oc-netinst:hide-transit-only-networks" {
    description
      "Not-supported deviation.";
    deviate not-supported;
  }

  deviation "/oc-netinst:network-instances/oc-netinst:network-instance/oc-netinst:protocols/oc-netinst:protocol/oc-netinst:ospfv2/oc-netinst:global/oc-netinst:config/oc-netinst:igp-shortcuts" {
    description
      "Not-supported deviation.";
    deviate not-supported;
  }

  deviation "/oc-netinst:network-instances/oc-netinst:network-instance/oc-netinst:protocols/oc-netinst:protocol/oc-netinst:ospfv2/oc-netinst:global/oc-netinst:config/oc-netinst:summary-route-cost-mode" {
    description
      "Not-supported deviation.";
    deviate not-supported;
  }

  deviation "/oc-netinst:network-instances/oc-netinst:network-instance/oc-netinst:protocols/oc-netinst:protocol/oc-netinst:ospfv2/oc-netinst:global/oc-netinst:graceful-restart/oc-netinst:state" {
    description
      "Not-supported deviation.";
    deviate not-supported;
  }

  deviation "/oc-netinst:network-instances/oc-netinst:network-instance/oc-netinst:protocols/oc-netinst:protocol/oc-netinst:ospfv2/oc-netinst:global/oc-netinst:timers/oc-netinst:lsa-generation/oc-netinst:state" {
    description
      "Not-supported deviation.";
    deviate not-supported;
  }

  deviation "/oc-netinst:network-instances/oc-netinst:network-instance/oc-netinst:protocols/oc-netinst:protocol/oc-netinst:ospfv2/oc-netinst:global/oc-netinst:timers/oc-netinst:max-metric/oc-netinst:state" {
    description
      "Not-supported deviation.";
    deviate not-supported;
  }

  deviation "/oc-netinst:network-instances/oc-netinst:network-instance/oc-netinst:protocols/oc-netinst:protocol/oc-netinst:ospfv2/oc-netinst:global/oc-netinst:timers/oc-netinst:spf/oc-netinst:state" {
    description
      "Not-supported deviation.";
    deviate not-supported;
  }

  deviation "/oc-netinst:network-instances/oc-netinst:network-instance/oc-netinst:protocols/oc-netinst:protocol/oc-netinst:pim/oc-netinst:global/oc-netinst:config" {
    description
      "Not-supported deviation.";
    deviate not-supported;
  }

  deviation "/oc-netinst:network-instances/oc-netinst:network-instance/oc-netinst:protocols/oc-netinst:protocol/oc-netinst:pim/oc-netinst:global/oc-netinst:sources-joined" {
    description
      "Not-supported deviation.";
    deviate not-supported;
  }

  deviation "/oc-netinst:network-instances/oc-netinst:network-instance/oc-netinst:protocols/oc-netinst:protocol/oc-netinst:pim/oc-netinst:global/oc-netinst:state" {
    description
      "Not-supported deviation.";
    deviate not-supported;
  }

  deviation "/oc-netinst:network-instances/oc-netinst:network-instance/oc-netinst:protocols/oc-netinst:protocol/oc-netinst:pim/oc-netinst:global/oc-netinst:rendezvous-points/oc-netinst:rendezvous-point/oc-netinst:state" {
    description
      "Not-supported deviation.";
    deviate not-supported;
  }

  deviation "/oc-netinst:network-instances/oc-netinst:network-instance/oc-netinst:protocols/oc-netinst:protocol/oc-netinst:pim/oc-netinst:global/oc-netinst:ssm/oc-netinst:state" {
    description
      "Not-supported deviation.";
    deviate not-supported;
  }

  deviation "/oc-netinst:network-instances/oc-netinst:network-instance/oc-netinst:protocols/oc-netinst:protocol/oc-netinst:pim/oc-netinst:interfaces/oc-netinst:interface/oc-netinst:interface-ref" {
    description
      "Not-supported deviation.";
    deviate not-supported;
  }

  deviation "/oc-netinst:network-instances/oc-netinst:network-instance/oc-netinst:protocols/oc-netinst:protocol/oc-netinst:pim/oc-netinst:interfaces/oc-netinst:interface/oc-netinst:config/oc-netinst:bsr-border" {
    description
      "Not-supported deviation.";
    deviate not-supported;
  }

  deviation "/oc-netinst:network-instances/oc-netinst:network-instance/oc-netinst:protocols/oc-netinst:protocol/oc-netinst:pim/oc-netinst:interfaces/oc-netinst:interface/oc-netinst:config/oc-netinst:maximum-groups" {
    description
      "Not-supported deviation.";
    deviate not-supported;
  }

  deviation "/oc-netinst:network-instances/oc-netinst:network-instance/oc-netinst:protocols/oc-netinst:protocol/oc-netinst:pim/oc-netinst:interfaces/oc-netinst:interface/oc-netinst:enable-bfd/oc-netinst:state" {
    description
      "Not-supported deviation.";
    deviate not-supported;
  }

  deviation "/oc-netinst:network-instances/oc-netinst:network-instance/oc-netinst:protocols/oc-netinst:protocol/oc-netinst:pim/oc-netinst:interfaces/oc-netinst:interface/oc-netinst:enable-bfd/oc-netinst:config/oc-netinst:desired-minimum-tx-interval" {
    description
      "Not-supported deviation.";
    deviate not-supported;
  }

  deviation "/oc-netinst:network-instances/oc-netinst:network-instance/oc-netinst:protocols/oc-netinst:protocol/oc-netinst:pim/oc-netinst:interfaces/oc-netinst:interface/oc-netinst:enable-bfd/oc-netinst:config/oc-netinst:detection-multiplier" {
    description
      "Not-supported deviation.";
    deviate not-supported;
  }

  deviation "/oc-netinst:network-instances/oc-netinst:network-instance/oc-netinst:protocols/oc-netinst:protocol/oc-netinst:pim/oc-netinst:interfaces/oc-netinst:interface/oc-netinst:enable-bfd/oc-netinst:config/oc-netinst:required-minimum-receive" {
    description
      "Not-supported deviation.";
    deviate not-supported;
  }

  deviation "/oc-netinst:network-instances/oc-netinst:network-instance/oc-netinst:protocols/oc-netinst:protocol/oc-netinst:pim/oc-netinst:interfaces/oc-netinst:interface/oc-netinst:state/oc-netinst:bsr-border" {
    description
      "Not-supported deviation.";
    deviate not-supported;
  }

  deviation "/oc-netinst:network-instances/oc-netinst:network-instance/oc-netinst:protocols/oc-netinst:protocol/oc-netinst:pim/oc-netinst:interfaces/oc-netinst:interface/oc-netinst:state/oc-netinst:maximum-groups" {
    description
      "Not-supported deviation.";
    deviate not-supported;
  }

  deviation "/oc-netinst:network-instances/oc-netinst:network-instance/oc-netinst:protocols/oc-netinst:protocol/oc-netinst:state/oc-netinst:default-metric" {
    description
      "Not-supported deviation.";
    deviate not-supported;
  }

  deviation "/oc-netinst:network-instances/oc-netinst:network-instance/oc-netinst:protocols/oc-netinst:protocol/oc-netinst:static-routes/oc-netinst:static/oc-netinst:config/oc-netinst:description" {
    description
      "Not-supported deviation.";
    deviate not-supported;
  }

  deviation "/oc-netinst:network-instances/oc-netinst:network-instance/oc-netinst:protocols/oc-netinst:protocol/oc-netinst:static-routes/oc-netinst:static/oc-netinst:next-hops/oc-netinst:next-hop/oc-netinst:enable-bfd" {
    description
      "Not-supported deviation.";
    deviate not-supported;
  }

  deviation "/oc-netinst:network-instances/oc-netinst:network-instance/oc-netinst:protocols/oc-netinst:protocol/oc-netinst:static-routes/oc-netinst:static/oc-netinst:next-hops/oc-netinst:next-hop/oc-netinst:state/oc-netinst:recurse" {
    description
      "Not-supported deviation.";
    deviate not-supported;
  }

  deviation "/oc-netinst:network-instances/oc-netinst:network-instance/oc-netinst:protocols/oc-netinst:protocol/oc-netinst:static-routes/oc-netinst:static/oc-netinst:state/oc-netinst:description" {
    description
      "Not-supported deviation.";
    deviate not-supported;
  }

  deviation "/oc-netinst:network-instances/oc-netinst:network-instance/oc-netinst:segment-routing/oc-netinst:srgbs/oc-netinst:srgb/oc-netinst:state" {
    description
      "Not-supported deviation.";
    deviate not-supported;
  }

  deviation "/oc-netinst:network-instances/oc-netinst:network-instance/oc-netinst:segment-routing/oc-netinst:srgbs/oc-netinst:srgb/oc-netinst:config/oc-netinst:ipv6-prefixes" {
    description
      "Not-supported deviation.";
    deviate not-supported;
  }

  deviation "/oc-netinst:network-instances/oc-netinst:network-instance/oc-netinst:segment-routing/oc-netinst:srlbs/oc-netinst:srlb/oc-netinst:state" {
    description
      "Not-supported deviation.";
    deviate not-supported;
  }

  deviation "/oc-netinst:network-instances/oc-netinst:network-instance/oc-netinst:segment-routing/oc-netinst:srlbs/oc-netinst:srlb/oc-netinst:config/oc-netinst:ipv6-prefix" {
    description
      "Not-supported deviation.";
    deviate not-supported;
  }

  deviation "/oc-netinst:network-instances/oc-netinst:network-instance/oc-netinst:segment-routing/oc-netinst:te-policies/oc-netinst:te-policy/oc-netinst:candidate-paths/oc-netinst:candidate-path/oc-netinst:segment-lists/oc-netinst:segment-list/oc-netinst:next-hops" {
    description
      "Not-supported deviation.";
    deviate not-supported;
  }

  deviation "/oc-netinst:network-instances/oc-netinst:network-instance/oc-netinst:segment-routing/oc-netinst:te-policies/oc-netinst:te-policy/oc-netinst:candidate-paths/oc-netinst:candidate-path/oc-netinst:segment-lists/oc-netinst:segment-list/oc-netinst:sids/oc-netinst:sid/oc-netinst:state/oc-netinst:mpls-tc" {
    description
      "Not-supported deviation.";
    deviate not-supported;
  }

  deviation "/oc-netinst:network-instances/oc-netinst:network-instance/oc-netinst:segment-routing/oc-netinst:te-policies/oc-netinst:te-policy/oc-netinst:candidate-paths/oc-netinst:candidate-path/oc-netinst:segment-lists/oc-netinst:segment-list/oc-netinst:sids/oc-netinst:sid/oc-netinst:state/oc-netinst:mpls-ttl" {
    description
      "Not-supported deviation.";
    deviate not-supported;
  }

  deviation "/oc-netinst:network-instances/oc-netinst:network-instance/oc-netinst:segment-routing/oc-netinst:te-policies/oc-netinst:te-policy/oc-netinst:candidate-paths/oc-netinst:candidate-path/oc-netinst:segment-lists/oc-netinst:segment-list/oc-netinst:state/oc-netinst:invalid-reason" {
    description
      "Not-supported deviation.";
    deviate not-supported;
  }

  deviation "/oc-netinst:network-instances/oc-netinst:network-instance/oc-netinst:segment-routing/oc-netinst:te-policies/oc-netinst:te-policy/oc-netinst:candidate-paths/oc-netinst:candidate-path/oc-netinst:segment-lists/oc-netinst:segment-list/oc-netinst:state/oc-netinst:counters/oc-netinst:out-labeled-octets" {
    description
      "Not-supported deviation.";
    deviate not-supported;
  }

  deviation "/oc-netinst:network-instances/oc-netinst:network-instance/oc-netinst:segment-routing/oc-netinst:te-policies/oc-netinst:te-policy/oc-netinst:candidate-paths/oc-netinst:candidate-path/oc-netinst:segment-lists/oc-netinst:segment-list/oc-netinst:state/oc-netinst:counters/oc-netinst:out-labeled-pkts" {
    description
      "Not-supported deviation.";
    deviate not-supported;
  }

  deviation "/oc-netinst:network-instances/oc-netinst:network-instance/oc-netinst:segment-routing/oc-netinst:te-policies/oc-netinst:te-policy/oc-netinst:candidate-paths/oc-netinst:candidate-path/oc-netinst:state/oc-netinst:active-since" {
    description
      "Not-supported deviation.";
    deviate not-supported;
  }

  deviation "/oc-netinst:network-instances/oc-netinst:network-instance/oc-netinst:segment-routing/oc-netinst:te-policies/oc-netinst:te-policy/oc-netinst:candidate-paths/oc-netinst:candidate-path/oc-netinst:state/oc-netinst:active-transitions" {
    description
      "Not-supported deviation.";
    deviate not-supported;
  }

  deviation "/oc-netinst:network-instances/oc-netinst:network-instance/oc-netinst:segment-routing/oc-netinst:te-policies/oc-netinst:te-policy/oc-netinst:candidate-paths/oc-netinst:candidate-path/oc-netinst:state/oc-netinst:name" {
    description
      "Not-supported deviation.";
    deviate not-supported;
  }

  deviation "/oc-netinst:network-instances/oc-netinst:network-instance/oc-netinst:segment-routing/oc-netinst:te-policies/oc-netinst:te-policy/oc-netinst:state/oc-netinst:active-since" {
    description
      "Not-supported deviation.";
    deviate not-supported;
  }

  deviation "/oc-netinst:network-instances/oc-netinst:network-instance/oc-netinst:segment-routing/oc-netinst:te-policies/oc-netinst:te-policy/oc-netinst:state/oc-netinst:active-transitions" {
    description
      "Not-supported deviation.";
    deviate not-supported;
  }

  deviation "/oc-netinst:network-instances/oc-netinst:network-instance/oc-netinst:segment-routing/oc-netinst:te-policies/oc-netinst:te-policy/oc-netinst:state/oc-netinst:counters/oc-netinst:in-labeled-octets" {
    description
      "Not-supported deviation.";
    deviate not-supported;
  }

  deviation "/oc-netinst:network-instances/oc-netinst:network-instance/oc-netinst:segment-routing/oc-netinst:te-policies/oc-netinst:te-policy/oc-netinst:state/oc-netinst:counters/oc-netinst:in-labeled-pkts" {
    description
      "Not-supported deviation.";
    deviate not-supported;
  }

  deviation "/oc-netinst:network-instances/oc-netinst:network-instance/oc-netinst:segment-routing/oc-netinst:te-policies/oc-netinst:te-policy/oc-netinst:state/oc-netinst:counters/oc-netinst:in-octets" {
    description
      "Not-supported deviation.";
    deviate not-supported;
  }

  deviation "/oc-netinst:network-instances/oc-netinst:network-instance/oc-netinst:segment-routing/oc-netinst:te-policies/oc-netinst:te-policy/oc-netinst:state/oc-netinst:counters/oc-netinst:in-pkts" {
    description
      "Not-supported deviation.";
    deviate not-supported;
  }

  deviation "/oc-netinst:network-instances/oc-netinst:network-instance/oc-netinst:segment-routing/oc-netinst:te-policies/oc-netinst:te-policy/oc-netinst:state/oc-netinst:counters/oc-netinst:out-labeled-octets" {
    description
      "Not-supported deviation.";
    deviate not-supported;
  }

  deviation "/oc-netinst:network-instances/oc-netinst:network-instance/oc-netinst:segment-routing/oc-netinst:te-policies/oc-netinst:te-policy/oc-netinst:state/oc-netinst:counters/oc-netinst:out-labeled-pkts" {
    description
      "Not-supported deviation.";
    deviate not-supported;
  }

  deviation "/oc-netinst:network-instances/oc-netinst:network-instance/oc-netinst:state/oc-netinst:fallback-network-instance" {
    description
      "Not-supported deviation.";
    deviate not-supported;
  }

  deviation "/oc-netinst:network-instances/oc-netinst:network-instance/oc-netinst:state/oc-netinst:name" {
    description
      "Not-supported deviation.";
    deviate not-supported;
  }

  deviation "/oc-netinst:network-instances/oc-netinst:network-instance/oc-netinst:state/oc-netinst:router-id" {
    description
      "Not-supported deviation.";
    deviate not-supported;
  }

  deviation "/oc-netinst:network-instances/oc-netinst:network-instance/oc-netinst:state/oc-netinst:type" {
    description
      "Not-supported deviation.";
    deviate not-supported;
  }

  deviation "/oc-netinst:network-instances/oc-netinst:network-instance/oc-netinst:tables/oc-netinst:table/oc-netinst:state" {
    description
      "Not-supported deviation.";
    deviate not-supported;
  }

  deviation "/oc-netinst:network-instances/oc-netinst:network-instance/oc-pgrmerrs:programming-errors/oc-pgrmerrs:ip-routes/oc-pgrmerrs:drop-routes/oc-pgrmerrs:drop/oc-pgrmerrs:state/oc-pgrmerrs:dest-component" {
    description
      "Not-supported deviation.";
    deviate not-supported;
  }

  deviation "/oc-netinst:network-instances/oc-netinst:network-instance/oc-pgrmerrs:programming-errors/oc-pgrmerrs:ip-routes/oc-pgrmerrs:failed-routes/oc-pgrmerrs:failed/oc-pgrmerrs:state/oc-pgrmerrs:dest-component" {
    description
      "Not-supported deviation.";
    deviate not-supported;
  }

  deviation "/oc-netinst:network-instances/oc-netinst:network-instance/oc-pgrmerrs:programming-errors/oc-pgrmerrs:ip-routes/oc-pgrmerrs:stale-routes/oc-pgrmerrs:stale/oc-pgrmerrs:state/oc-pgrmerrs:dest-component" {
    description
      "Not-supported deviation.";
    deviate not-supported;
  }
}
