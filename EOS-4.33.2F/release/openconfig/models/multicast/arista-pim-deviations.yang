module arista-pim-deviations {
  namespace "http://arista.com/yang/openconfig/pim/deviations";
  prefix arista-pim-deviations;

  import openconfig-network-instance {
    prefix oc-netinst;
  }
  import openconfig-extensions {
    prefix oc-ext;
  }

  organization
    "Arista Networks, Inc.";
  contact
    "Arista Networks, Inc.
     Product Support";
  description
    "This module contains OpenConfig PIM deviations in Arista EOS.

     Copyright (c) 2024 Arista Networks, Inc. All rights reserved.";
  oc-ext:openconfig-version "1.2.0";

  revision 2024-10-14 {
    description
     "Add must deviation to restrict PIM_MODE_DENSE";
    reference
    "1.2.0";
  }

  revision 2024-09-25 {
    description
     "Updated PIM interfaces leaf value ranges";
    reference
    "1.1.0";
  }

  revision 2024-07-10 {
    description
     "Changed PIM dead-timer type to be a decimal64";
    reference
    "1.0.0";
  }

  deviation "/oc-netinst:network-instances/oc-netinst:network-instance/oc-netinst:protocols/oc-netinst:protocol/oc-netinst:pim/oc-netinst:interfaces/oc-netinst:interface/oc-netinst:config/oc-netinst:dead-timer" {
    description
      "dead timer is a float value 3.5 by default as mandated by RFC7761";
    deviate replace {
      type decimal64 {
          fraction-digits 2;
          range "1.5..65535";
      }
    }
  }

  deviation "/oc-netinst:network-instances/oc-netinst:network-instance/oc-netinst:protocols/oc-netinst:protocol/oc-netinst:pim/oc-netinst:interfaces/oc-netinst:interface/oc-netinst:state/oc-netinst:dead-timer" {
    description
      "dead timer is a float value 3.5 by default as mandated by RFC7761";
    deviate replace {
      type decimal64 {
          fraction-digits 2;
          range "1.5..65535";
      }
    }
  }

  deviation "/oc-netinst:network-instances/oc-netinst:network-instance/oc-netinst:protocols/oc-netinst:protocol/oc-netinst:pim/oc-netinst:interfaces/oc-netinst:interface/oc-netinst:config/oc-netinst:join-prune-interval" {
    description
      "Change type from uint8 to uint16";
    deviate replace {
      type uint16 {
        range "1..18724";
      }
    }
  }

  deviation "/oc-netinst:network-instances/oc-netinst:network-instance/oc-netinst:protocols/oc-netinst:protocol/oc-netinst:pim/oc-netinst:interfaces/oc-netinst:interface/oc-netinst:state/oc-netinst:join-prune-interval" {
    description
      "Change type from uint8 to uint16";
    deviate replace {
      type uint16 {
        range "1..18724";
      }
    }
  }

  deviation "/oc-netinst:network-instances/oc-netinst:network-instance/oc-netinst:protocols/oc-netinst:protocol/oc-netinst:pim/oc-netinst:interfaces/oc-netinst:interface/oc-netinst:config/oc-netinst:hello-interval" {
    description
      "Change type from uint8 to uint16";
    deviate replace {
      type uint16 {
        range "1..65535";
      }
    }
  }

 deviation "/oc-netinst:network-instances/oc-netinst:network-instance/oc-netinst:protocols/oc-netinst:protocol/oc-netinst:pim/oc-netinst:interfaces/oc-netinst:interface/oc-netinst:state/oc-netinst:hello-interval" {
    description
      "Change type from uint8 to uint16";
    deviate replace {
      type uint16 {
        range "1..65535";
      }
    }
  }

  deviation "/oc-netinst:network-instances/oc-netinst:network-instance/oc-netinst:protocols/oc-netinst:protocol/oc-netinst:pim/oc-netinst:interfaces/oc-netinst:interface/oc-netinst:config/oc-netinst:mode" {
    description
      "EOS does not support PIM_MODE_DENSE";
    deviate add {
      must "../mode != 'PIM_MODE_DENSE'" {
        error-message "EOS does not support PIM_MODE_DENSE";
      }
    }
  }
}
