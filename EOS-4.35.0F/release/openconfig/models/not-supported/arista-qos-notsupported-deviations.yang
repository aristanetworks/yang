module arista-qos-notsupported-deviations {
  namespace "http://arista.com/yang/openconfig/qos/notsupported-deviations";
  prefix arista-qos-notsupported-deviations;

  import openconfig-hercules-qos {
    prefix herc-qos;
  }
  import openconfig-qos {
    prefix oc-qos;
  }

  organization
    "Arista Networks, Inc.";
  contact
    "Arista Networks, Inc.
     Product Support";
  description
    "This module contains OpenConfig qos deviations in Arista EOS.
     Copyright (c) 2020 Arista Networks, Inc. All rights reserved.";

  revision 2025-10-02 {
    description
      "Auto-generated not-supported deviations for unsupported paths";
  }

  deviation "/oc-qos:qos/oc-qos:buffer-allocation-profiles" {
    description
      "Not-supported deviation.";
    deviate not-supported;
  }

  deviation "/oc-qos:qos/oc-qos:config" {
    description
      "Not-supported deviation.";
    deviate not-supported;
  }

  deviation "/oc-qos:qos/oc-qos:state" {
    description
      "Not-supported deviation.";
    deviate not-supported;
  }

  deviation "/oc-qos:qos/oc-qos:classifiers/oc-qos:classifier/oc-qos:terms/oc-qos:term/oc-qos:actions/oc-qos:remark" {
    description
      "Not-supported deviation.";
    deviate not-supported;
  }

  deviation "/oc-qos:qos/oc-qos:classifiers/oc-qos:classifier/oc-qos:terms/oc-qos:term/oc-qos:conditions/oc-qos:l2" {
    description
      "Not-supported deviation.";
    deviate not-supported;
  }

  deviation "/oc-qos:qos/oc-qos:classifiers/oc-qos:classifier/oc-qos:terms/oc-qos:term/oc-qos:conditions/oc-qos:mpls" {
    description
      "Not-supported deviation.";
    deviate not-supported;
  }

  deviation "/oc-qos:qos/oc-qos:classifiers/oc-qos:classifier/oc-qos:terms/oc-qos:term/oc-qos:conditions/oc-qos:transport" {
    description
      "Not-supported deviation.";
    deviate not-supported;
  }

  deviation "/oc-qos:qos/oc-qos:classifiers/oc-qos:classifier/oc-qos:terms/oc-qos:term/oc-qos:conditions/oc-qos:ipv4/oc-qos:icmpv4" {
    description
      "Not-supported deviation.";
    deviate not-supported;
  }

  deviation "/oc-qos:qos/oc-qos:classifiers/oc-qos:classifier/oc-qos:terms/oc-qos:term/oc-qos:conditions/oc-qos:ipv4/oc-qos:config/oc-qos:destination-address" {
    description
      "Not-supported deviation.";
    deviate not-supported;
  }

  deviation "/oc-qos:qos/oc-qos:classifiers/oc-qos:classifier/oc-qos:terms/oc-qos:term/oc-qos:conditions/oc-qos:ipv4/oc-qos:config/oc-qos:destination-address-prefix-set" {
    description
      "Not-supported deviation.";
    deviate not-supported;
  }

  deviation "/oc-qos:qos/oc-qos:classifiers/oc-qos:classifier/oc-qos:terms/oc-qos:term/oc-qos:conditions/oc-qos:ipv4/oc-qos:config/oc-qos:hop-limit" {
    description
      "Not-supported deviation.";
    deviate not-supported;
  }

  deviation "/oc-qos:qos/oc-qos:classifiers/oc-qos:classifier/oc-qos:terms/oc-qos:term/oc-qos:conditions/oc-qos:ipv4/oc-qos:config/oc-qos:length" {
    description
      "Not-supported deviation.";
    deviate not-supported;
  }

  deviation "/oc-qos:qos/oc-qos:classifiers/oc-qos:classifier/oc-qos:terms/oc-qos:term/oc-qos:conditions/oc-qos:ipv4/oc-qos:config/oc-qos:protocol" {
    description
      "Not-supported deviation.";
    deviate not-supported;
  }

  deviation "/oc-qos:qos/oc-qos:classifiers/oc-qos:classifier/oc-qos:terms/oc-qos:term/oc-qos:conditions/oc-qos:ipv4/oc-qos:config/oc-qos:source-address" {
    description
      "Not-supported deviation.";
    deviate not-supported;
  }

  deviation "/oc-qos:qos/oc-qos:classifiers/oc-qos:classifier/oc-qos:terms/oc-qos:term/oc-qos:conditions/oc-qos:ipv4/oc-qos:config/oc-qos:source-address-prefix-set" {
    description
      "Not-supported deviation.";
    deviate not-supported;
  }

  deviation "/oc-qos:qos/oc-qos:classifiers/oc-qos:classifier/oc-qos:terms/oc-qos:term/oc-qos:conditions/oc-qos:ipv4/oc-qos:state/oc-qos:destination-address" {
    description
      "Not-supported deviation.";
    deviate not-supported;
  }

  deviation "/oc-qos:qos/oc-qos:classifiers/oc-qos:classifier/oc-qos:terms/oc-qos:term/oc-qos:conditions/oc-qos:ipv4/oc-qos:state/oc-qos:destination-address-prefix-set" {
    description
      "Not-supported deviation.";
    deviate not-supported;
  }

  deviation "/oc-qos:qos/oc-qos:classifiers/oc-qos:classifier/oc-qos:terms/oc-qos:term/oc-qos:conditions/oc-qos:ipv4/oc-qos:state/oc-qos:hop-limit" {
    description
      "Not-supported deviation.";
    deviate not-supported;
  }

  deviation "/oc-qos:qos/oc-qos:classifiers/oc-qos:classifier/oc-qos:terms/oc-qos:term/oc-qos:conditions/oc-qos:ipv4/oc-qos:state/oc-qos:length" {
    description
      "Not-supported deviation.";
    deviate not-supported;
  }

  deviation "/oc-qos:qos/oc-qos:classifiers/oc-qos:classifier/oc-qos:terms/oc-qos:term/oc-qos:conditions/oc-qos:ipv4/oc-qos:state/oc-qos:protocol" {
    description
      "Not-supported deviation.";
    deviate not-supported;
  }

  deviation "/oc-qos:qos/oc-qos:classifiers/oc-qos:classifier/oc-qos:terms/oc-qos:term/oc-qos:conditions/oc-qos:ipv4/oc-qos:state/oc-qos:source-address" {
    description
      "Not-supported deviation.";
    deviate not-supported;
  }

  deviation "/oc-qos:qos/oc-qos:classifiers/oc-qos:classifier/oc-qos:terms/oc-qos:term/oc-qos:conditions/oc-qos:ipv4/oc-qos:state/oc-qos:source-address-prefix-set" {
    description
      "Not-supported deviation.";
    deviate not-supported;
  }

  deviation "/oc-qos:qos/oc-qos:classifiers/oc-qos:classifier/oc-qos:terms/oc-qos:term/oc-qos:conditions/oc-qos:ipv6/oc-qos:icmpv6" {
    description
      "Not-supported deviation.";
    deviate not-supported;
  }

  deviation "/oc-qos:qos/oc-qos:classifiers/oc-qos:classifier/oc-qos:terms/oc-qos:term/oc-qos:conditions/oc-qos:ipv6/oc-qos:config/oc-qos:destination-address" {
    description
      "Not-supported deviation.";
    deviate not-supported;
  }

  deviation "/oc-qos:qos/oc-qos:classifiers/oc-qos:classifier/oc-qos:terms/oc-qos:term/oc-qos:conditions/oc-qos:ipv6/oc-qos:config/oc-qos:destination-address-prefix-set" {
    description
      "Not-supported deviation.";
    deviate not-supported;
  }

  deviation "/oc-qos:qos/oc-qos:classifiers/oc-qos:classifier/oc-qos:terms/oc-qos:term/oc-qos:conditions/oc-qos:ipv6/oc-qos:config/oc-qos:destination-flow-label" {
    description
      "Not-supported deviation.";
    deviate not-supported;
  }

  deviation "/oc-qos:qos/oc-qos:classifiers/oc-qos:classifier/oc-qos:terms/oc-qos:term/oc-qos:conditions/oc-qos:ipv6/oc-qos:config/oc-qos:hop-limit" {
    description
      "Not-supported deviation.";
    deviate not-supported;
  }

  deviation "/oc-qos:qos/oc-qos:classifiers/oc-qos:classifier/oc-qos:terms/oc-qos:term/oc-qos:conditions/oc-qos:ipv6/oc-qos:config/oc-qos:length" {
    description
      "Not-supported deviation.";
    deviate not-supported;
  }

  deviation "/oc-qos:qos/oc-qos:classifiers/oc-qos:classifier/oc-qos:terms/oc-qos:term/oc-qos:conditions/oc-qos:ipv6/oc-qos:config/oc-qos:protocol" {
    description
      "Not-supported deviation.";
    deviate not-supported;
  }

  deviation "/oc-qos:qos/oc-qos:classifiers/oc-qos:classifier/oc-qos:terms/oc-qos:term/oc-qos:conditions/oc-qos:ipv6/oc-qos:config/oc-qos:source-address" {
    description
      "Not-supported deviation.";
    deviate not-supported;
  }

  deviation "/oc-qos:qos/oc-qos:classifiers/oc-qos:classifier/oc-qos:terms/oc-qos:term/oc-qos:conditions/oc-qos:ipv6/oc-qos:config/oc-qos:source-address-prefix-set" {
    description
      "Not-supported deviation.";
    deviate not-supported;
  }

  deviation "/oc-qos:qos/oc-qos:classifiers/oc-qos:classifier/oc-qos:terms/oc-qos:term/oc-qos:conditions/oc-qos:ipv6/oc-qos:config/oc-qos:source-flow-label" {
    description
      "Not-supported deviation.";
    deviate not-supported;
  }

  deviation "/oc-qos:qos/oc-qos:classifiers/oc-qos:classifier/oc-qos:terms/oc-qos:term/oc-qos:conditions/oc-qos:ipv6/oc-qos:state/oc-qos:destination-address" {
    description
      "Not-supported deviation.";
    deviate not-supported;
  }

  deviation "/oc-qos:qos/oc-qos:classifiers/oc-qos:classifier/oc-qos:terms/oc-qos:term/oc-qos:conditions/oc-qos:ipv6/oc-qos:state/oc-qos:destination-address-prefix-set" {
    description
      "Not-supported deviation.";
    deviate not-supported;
  }

  deviation "/oc-qos:qos/oc-qos:classifiers/oc-qos:classifier/oc-qos:terms/oc-qos:term/oc-qos:conditions/oc-qos:ipv6/oc-qos:state/oc-qos:destination-flow-label" {
    description
      "Not-supported deviation.";
    deviate not-supported;
  }

  deviation "/oc-qos:qos/oc-qos:classifiers/oc-qos:classifier/oc-qos:terms/oc-qos:term/oc-qos:conditions/oc-qos:ipv6/oc-qos:state/oc-qos:hop-limit" {
    description
      "Not-supported deviation.";
    deviate not-supported;
  }

  deviation "/oc-qos:qos/oc-qos:classifiers/oc-qos:classifier/oc-qos:terms/oc-qos:term/oc-qos:conditions/oc-qos:ipv6/oc-qos:state/oc-qos:length" {
    description
      "Not-supported deviation.";
    deviate not-supported;
  }

  deviation "/oc-qos:qos/oc-qos:classifiers/oc-qos:classifier/oc-qos:terms/oc-qos:term/oc-qos:conditions/oc-qos:ipv6/oc-qos:state/oc-qos:protocol" {
    description
      "Not-supported deviation.";
    deviate not-supported;
  }

  deviation "/oc-qos:qos/oc-qos:classifiers/oc-qos:classifier/oc-qos:terms/oc-qos:term/oc-qos:conditions/oc-qos:ipv6/oc-qos:state/oc-qos:source-address" {
    description
      "Not-supported deviation.";
    deviate not-supported;
  }

  deviation "/oc-qos:qos/oc-qos:classifiers/oc-qos:classifier/oc-qos:terms/oc-qos:term/oc-qos:conditions/oc-qos:ipv6/oc-qos:state/oc-qos:source-address-prefix-set" {
    description
      "Not-supported deviation.";
    deviate not-supported;
  }

  deviation "/oc-qos:qos/oc-qos:classifiers/oc-qos:classifier/oc-qos:terms/oc-qos:term/oc-qos:conditions/oc-qos:ipv6/oc-qos:state/oc-qos:source-flow-label" {
    description
      "Not-supported deviation.";
    deviate not-supported;
  }

  deviation "/oc-qos:qos/oc-qos:forwarding-groups/oc-qos:forwarding-group/oc-qos:config/oc-qos:fabric-priority" {
    description
      "Not-supported deviation.";
    deviate not-supported;
  }

  deviation "/oc-qos:qos/oc-qos:forwarding-groups/oc-qos:forwarding-group/oc-qos:config/oc-qos:multicast-output-queue" {
    description
      "Not-supported deviation.";
    deviate not-supported;
  }

  deviation "/oc-qos:qos/oc-qos:forwarding-groups/oc-qos:forwarding-group/oc-qos:config/oc-qos:unicast-output-queue" {
    description
      "Not-supported deviation.";
    deviate not-supported;
  }

  deviation "/oc-qos:qos/oc-qos:forwarding-groups/oc-qos:forwarding-group/oc-qos:state/oc-qos:fabric-priority" {
    description
      "Not-supported deviation.";
    deviate not-supported;
  }

  deviation "/oc-qos:qos/oc-qos:forwarding-groups/oc-qos:forwarding-group/oc-qos:state/oc-qos:multicast-output-queue" {
    description
      "Not-supported deviation.";
    deviate not-supported;
  }

  deviation "/oc-qos:qos/oc-qos:forwarding-groups/oc-qos:forwarding-group/oc-qos:state/oc-qos:unicast-output-queue" {
    description
      "Not-supported deviation.";
    deviate not-supported;
  }

  deviation "/oc-qos:qos/oc-qos:interfaces/oc-qos:interface/oc-qos:input/oc-qos:config" {
    description
      "Not-supported deviation.";
    deviate not-supported;
  }

  deviation "/oc-qos:qos/oc-qos:interfaces/oc-qos:interface/oc-qos:input/oc-qos:queues" {
    description
      "Not-supported deviation.";
    deviate not-supported;
  }

  deviation "/oc-qos:qos/oc-qos:interfaces/oc-qos:interface/oc-qos:input/oc-qos:state" {
    description
      "Not-supported deviation.";
    deviate not-supported;
  }

  deviation "/oc-qos:qos/oc-qos:interfaces/oc-qos:interface/oc-qos:input/oc-qos:virtual-output-queues" {
    description
      "Not-supported deviation.";
    deviate not-supported;
  }

  deviation "/oc-qos:qos/oc-qos:interfaces/oc-qos:interface/oc-qos:input/oc-qos:scheduler-policy/oc-qos:config" {
    description
      "Not-supported deviation.";
    deviate not-supported;
  }

  deviation "/oc-qos:qos/oc-qos:interfaces/oc-qos:interface/oc-qos:input/oc-qos:scheduler-policy/oc-qos:schedulers/oc-qos:scheduler/oc-qos:state/oc-qos:violating-octets" {
    description
      "Not-supported deviation.";
    deviate not-supported;
  }

  deviation "/oc-qos:qos/oc-qos:interfaces/oc-qos:interface/oc-qos:input/oc-qos:scheduler-policy/oc-qos:schedulers/oc-qos:scheduler/oc-qos:state/oc-qos:violating-pkts" {
    description
      "Not-supported deviation.";
    deviate not-supported;
  }

  deviation "/oc-qos:qos/oc-qos:interfaces/oc-qos:interface/oc-qos:output/oc-qos:classifiers" {
    description
      "Not-supported deviation.";
    deviate not-supported;
  }

  deviation "/oc-qos:qos/oc-qos:interfaces/oc-qos:interface/oc-qos:output/oc-qos:config" {
    description
      "Not-supported deviation.";
    deviate not-supported;
  }

  deviation "/oc-qos:qos/oc-qos:interfaces/oc-qos:interface/oc-qos:output/oc-qos:state" {
    description
      "Not-supported deviation.";
    deviate not-supported;
  }

  deviation "/oc-qos:qos/oc-qos:interfaces/oc-qos:interface/oc-qos:output/oc-qos:queues/oc-qos:queue/oc-qos:state/oc-qos:avg-queue-len" {
    description
      "Not-supported deviation.";
    deviate not-supported;
  }

  deviation "/oc-qos:qos/oc-qos:interfaces/oc-qos:interface/oc-qos:output/oc-qos:queues/oc-qos:queue/oc-qos:state/oc-qos:ecn-marked-octets" {
    description
      "Not-supported deviation.";
    deviate not-supported;
  }

  deviation "/oc-qos:qos/oc-qos:interfaces/oc-qos:interface/oc-qos:output/oc-qos:queues/oc-qos:queue/oc-qos:state/oc-qos:ecn-selected-octets" {
    description
      "Not-supported deviation.";
    deviate not-supported;
  }

  deviation "/oc-qos:qos/oc-qos:interfaces/oc-qos:interface/oc-qos:output/oc-qos:queues/oc-qos:queue/oc-qos:state/oc-qos:max-queue-len" {
    description
      "Not-supported deviation.";
    deviate not-supported;
  }

  deviation "/oc-qos:qos/oc-qos:interfaces/oc-qos:interface/oc-qos:output/oc-qos:scheduler-policy/oc-qos:schedulers" {
    description
      "Not-supported deviation.";
    deviate not-supported;
  }

  deviation "/oc-qos:qos/oc-qos:queue-management-profiles/oc-qos:queue-management-profile/oc-qos:red" {
    description
      "Not-supported deviation.";
    deviate not-supported;
  }

  deviation "/oc-qos:qos/oc-qos:queue-management-profiles/oc-qos:queue-management-profile/oc-qos:wred/oc-qos:uniform/oc-qos:config/oc-qos:max-threshold-percent" {
    description
      "Not-supported deviation.";
    deviate not-supported;
  }

  deviation "/oc-qos:qos/oc-qos:queue-management-profiles/oc-qos:queue-management-profile/oc-qos:wred/oc-qos:uniform/oc-qos:config/oc-qos:min-threshold-percent" {
    description
      "Not-supported deviation.";
    deviate not-supported;
  }

  deviation "/oc-qos:qos/oc-qos:queue-management-profiles/oc-qos:queue-management-profile/oc-qos:wred/oc-qos:uniform/oc-qos:state/oc-qos:max-threshold-percent" {
    description
      "Not-supported deviation.";
    deviate not-supported;
  }

  deviation "/oc-qos:qos/oc-qos:queue-management-profiles/oc-qos:queue-management-profile/oc-qos:wred/oc-qos:uniform/oc-qos:state/oc-qos:min-threshold-percent" {
    description
      "Not-supported deviation.";
    deviate not-supported;
  }

  deviation "/oc-qos:qos/oc-qos:queues/oc-qos:queue/oc-qos:config/herc-qos:id" {
    description
      "Not-supported deviation.";
    deviate not-supported;
  }

  deviation "/oc-qos:qos/oc-qos:queues/oc-qos:queue/oc-qos:config/oc-qos:queue-id" {
    description
      "Not-supported deviation.";
    deviate not-supported;
  }

  deviation "/oc-qos:qos/oc-qos:queues/oc-qos:queue/oc-qos:state/herc-qos:id" {
    description
      "Not-supported deviation.";
    deviate not-supported;
  }

  deviation "/oc-qos:qos/oc-qos:queues/oc-qos:queue/oc-qos:state/oc-qos:queue-id" {
    description
      "Not-supported deviation.";
    deviate not-supported;
  }

  deviation "/oc-qos:qos/oc-qos:scheduler-policies/oc-qos:scheduler-policy/oc-qos:schedulers/oc-qos:scheduler/oc-qos:output" {
    description
      "Not-supported deviation.";
    deviate not-supported;
  }

  deviation "/oc-qos:qos/oc-qos:scheduler-policies/oc-qos:scheduler-policy/oc-qos:schedulers/oc-qos:scheduler/oc-qos:two-rate-three-color" {
    description
      "Not-supported deviation.";
    deviate not-supported;
  }

  deviation "/oc-qos:qos/oc-qos:scheduler-policies/oc-qos:scheduler-policy/oc-qos:schedulers/oc-qos:scheduler/oc-qos:one-rate-two-color/oc-qos:conform-action" {
    description
      "Not-supported deviation.";
    deviate not-supported;
  }

  deviation "/oc-qos:qos/oc-qos:scheduler-policies/oc-qos:scheduler-policy/oc-qos:schedulers/oc-qos:scheduler/oc-qos:one-rate-two-color/oc-qos:config/oc-qos:cir-pct-remaining" {
    description
      "Not-supported deviation.";
    deviate not-supported;
  }

  deviation "/oc-qos:qos/oc-qos:scheduler-policies/oc-qos:scheduler-policy/oc-qos:schedulers/oc-qos:scheduler/oc-qos:one-rate-two-color/oc-qos:config/oc-qos:max-queue-depth-bytes" {
    description
      "Not-supported deviation.";
    deviate not-supported;
  }

  deviation "/oc-qos:qos/oc-qos:scheduler-policies/oc-qos:scheduler-policy/oc-qos:schedulers/oc-qos:scheduler/oc-qos:one-rate-two-color/oc-qos:config/oc-qos:max-queue-depth-packets" {
    description
      "Not-supported deviation.";
    deviate not-supported;
  }

  deviation "/oc-qos:qos/oc-qos:scheduler-policies/oc-qos:scheduler-policy/oc-qos:schedulers/oc-qos:scheduler/oc-qos:one-rate-two-color/oc-qos:config/oc-qos:max-queue-depth-percent" {
    description
      "Not-supported deviation.";
    deviate not-supported;
  }

  deviation "/oc-qos:qos/oc-qos:scheduler-policies/oc-qos:scheduler-policy/oc-qos:schedulers/oc-qos:scheduler/oc-qos:one-rate-two-color/oc-qos:exceed-action/oc-qos:config/oc-qos:set-dot1p" {
    description
      "Not-supported deviation.";
    deviate not-supported;
  }

  deviation "/oc-qos:qos/oc-qos:scheduler-policies/oc-qos:scheduler-policy/oc-qos:schedulers/oc-qos:scheduler/oc-qos:one-rate-two-color/oc-qos:exceed-action/oc-qos:config/oc-qos:set-dscp" {
    description
      "Not-supported deviation.";
    deviate not-supported;
  }

  deviation "/oc-qos:qos/oc-qos:scheduler-policies/oc-qos:scheduler-policy/oc-qos:schedulers/oc-qos:scheduler/oc-qos:one-rate-two-color/oc-qos:exceed-action/oc-qos:config/oc-qos:set-mpls-tc" {
    description
      "Not-supported deviation.";
    deviate not-supported;
  }

  deviation "/oc-qos:qos/oc-qos:scheduler-policies/oc-qos:scheduler-policy/oc-qos:schedulers/oc-qos:scheduler/oc-qos:one-rate-two-color/oc-qos:exceed-action/oc-qos:state/oc-qos:set-dot1p" {
    description
      "Not-supported deviation.";
    deviate not-supported;
  }

  deviation "/oc-qos:qos/oc-qos:scheduler-policies/oc-qos:scheduler-policy/oc-qos:schedulers/oc-qos:scheduler/oc-qos:one-rate-two-color/oc-qos:exceed-action/oc-qos:state/oc-qos:set-dscp" {
    description
      "Not-supported deviation.";
    deviate not-supported;
  }

  deviation "/oc-qos:qos/oc-qos:scheduler-policies/oc-qos:scheduler-policy/oc-qos:schedulers/oc-qos:scheduler/oc-qos:one-rate-two-color/oc-qos:exceed-action/oc-qos:state/oc-qos:set-mpls-tc" {
    description
      "Not-supported deviation.";
    deviate not-supported;
  }

  deviation "/oc-qos:qos/oc-qos:scheduler-policies/oc-qos:scheduler-policy/oc-qos:schedulers/oc-qos:scheduler/oc-qos:one-rate-two-color/oc-qos:state/oc-qos:cir-pct-remaining" {
    description
      "Not-supported deviation.";
    deviate not-supported;
  }

  deviation "/oc-qos:qos/oc-qos:scheduler-policies/oc-qos:scheduler-policy/oc-qos:schedulers/oc-qos:scheduler/oc-qos:one-rate-two-color/oc-qos:state/oc-qos:max-queue-depth-bytes" {
    description
      "Not-supported deviation.";
    deviate not-supported;
  }

  deviation "/oc-qos:qos/oc-qos:scheduler-policies/oc-qos:scheduler-policy/oc-qos:schedulers/oc-qos:scheduler/oc-qos:one-rate-two-color/oc-qos:state/oc-qos:max-queue-depth-packets" {
    description
      "Not-supported deviation.";
    deviate not-supported;
  }

  deviation "/oc-qos:qos/oc-qos:scheduler-policies/oc-qos:scheduler-policy/oc-qos:schedulers/oc-qos:scheduler/oc-qos:one-rate-two-color/oc-qos:state/oc-qos:max-queue-depth-percent" {
    description
      "Not-supported deviation.";
    deviate not-supported;
  }
}
