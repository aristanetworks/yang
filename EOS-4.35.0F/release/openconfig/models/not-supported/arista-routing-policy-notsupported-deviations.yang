module arista-routing-policy-notsupported-deviations {
  namespace "http://arista.com/yang/openconfig/routing-policy/notsupported-deviations";
  prefix arista-routing-policy-notsupported-deviations;

  import openconfig-bgp-policy {
    prefix oc-bgp-pol;
  }
  import openconfig-isis-policy {
    prefix oc-isis-pol;
  }
  import openconfig-ospf-policy {
    prefix oc-ospf-pol;
  }
  import openconfig-routing-policy {
    prefix oc-rpol;
  }

  organization
    "Arista Networks, Inc.";
  contact
    "Arista Networks, Inc.
     Product Support";
  description
    "This module contains OpenConfig routing-policy deviations in Arista EOS.
     Copyright (c) 2020 Arista Networks, Inc. All rights reserved.";

  revision 2025-10-02 {
    description
      "Auto-generated not-supported deviations for unsupported paths";
  }

  deviation "/oc-rpol:routing-policy/oc-rpol:policy-definitions/oc-rpol:policy-definition/oc-rpol:statements/oc-rpol:statement/oc-rpol:actions/oc-rpol:set-tag" {
    description
      "Not-supported deviation.";
    deviate not-supported;
  }

  deviation "/oc-rpol:routing-policy/oc-rpol:policy-definitions/oc-rpol:policy-definition/oc-rpol:statements/oc-rpol:statement/oc-rpol:actions/oc-bgp-pol:bgp-actions/oc-bgp-pol:set-as-path-prepend/oc-bgp-pol:config/oc-bgp-pol:use-last-as" {
    description
      "Not-supported deviation.";
    deviate not-supported;
  }

  deviation "/oc-rpol:routing-policy/oc-rpol:policy-definitions/oc-rpol:policy-definition/oc-rpol:statements/oc-rpol:statement/oc-rpol:actions/oc-bgp-pol:bgp-actions/oc-bgp-pol:set-as-path-prepend/oc-bgp-pol:state/oc-bgp-pol:use-last-as" {
    description
      "Not-supported deviation.";
    deviate not-supported;
  }

  deviation "/oc-rpol:routing-policy/oc-rpol:policy-definitions/oc-rpol:policy-definition/oc-rpol:statements/oc-rpol:statement/oc-rpol:actions/oc-isis-pol:isis-actions/oc-isis-pol:config/oc-isis-pol:set-metric-type" {
    description
      "Not-supported deviation.";
    deviate not-supported;
  }

  deviation "/oc-rpol:routing-policy/oc-rpol:policy-definitions/oc-rpol:policy-definition/oc-rpol:statements/oc-rpol:statement/oc-rpol:actions/oc-isis-pol:isis-actions/oc-isis-pol:state/oc-isis-pol:set-metric-type" {
    description
      "Not-supported deviation.";
    deviate not-supported;
  }

  deviation "/oc-rpol:routing-policy/oc-rpol:policy-definitions/oc-rpol:policy-definition/oc-rpol:statements/oc-rpol:statement/oc-rpol:actions/oc-ospf-pol:ospf-actions/oc-ospf-pol:config" {
    description
      "Not-supported deviation.";
    deviate not-supported;
  }

  deviation "/oc-rpol:routing-policy/oc-rpol:policy-definitions/oc-rpol:policy-definition/oc-rpol:statements/oc-rpol:statement/oc-rpol:actions/oc-ospf-pol:ospf-actions/oc-ospf-pol:state" {
    description
      "Not-supported deviation.";
    deviate not-supported;
  }

  deviation "/oc-rpol:routing-policy/oc-rpol:policy-definitions/oc-rpol:policy-definition/oc-rpol:statements/oc-rpol:statement/oc-rpol:conditions/oc-isis-pol:isis-conditions" {
    description
      "Not-supported deviation.";
    deviate not-supported;
  }

  deviation "/oc-rpol:routing-policy/oc-rpol:policy-definitions/oc-rpol:policy-definition/oc-rpol:statements/oc-rpol:statement/oc-rpol:conditions/oc-ospf-pol:ospf-conditions" {
    description
      "Not-supported deviation.";
    deviate not-supported;
  }

  deviation "/oc-rpol:routing-policy/oc-rpol:policy-definitions/oc-rpol:policy-definition/oc-rpol:statements/oc-rpol:statement/oc-rpol:conditions/oc-rpol:match-neighbor-set" {
    description
      "Not-supported deviation.";
    deviate not-supported;
  }

  deviation "/oc-rpol:routing-policy/oc-rpol:policy-definitions/oc-rpol:policy-definition/oc-rpol:statements/oc-rpol:statement/oc-rpol:conditions/oc-bgp-pol:bgp-conditions/oc-bgp-pol:ext-community-count" {
    description
      "Not-supported deviation.";
    deviate not-supported;
  }

  deviation "/oc-rpol:routing-policy/oc-rpol:policy-definitions/oc-rpol:policy-definition/oc-rpol:statements/oc-rpol:statement/oc-rpol:conditions/oc-bgp-pol:bgp-conditions/oc-bgp-pol:match-as-path-set" {
    description
      "Not-supported deviation.";
    deviate not-supported;
  }

  deviation "/oc-rpol:routing-policy/oc-rpol:policy-definitions/oc-rpol:policy-definition/oc-rpol:statements/oc-rpol:statement/oc-rpol:conditions/oc-bgp-pol:bgp-conditions/oc-bgp-pol:config/oc-bgp-pol:afi-safi-in" {
    description
      "Not-supported deviation.";
    deviate not-supported;
  }

  deviation "/oc-rpol:routing-policy/oc-rpol:policy-definitions/oc-rpol:policy-definition/oc-rpol:statements/oc-rpol:statement/oc-rpol:conditions/oc-bgp-pol:bgp-conditions/oc-bgp-pol:state/oc-bgp-pol:afi-safi-in" {
    description
      "Not-supported deviation.";
    deviate not-supported;
  }

  deviation "/oc-rpol:routing-policy/oc-rpol:policy-definitions/oc-rpol:policy-definition/oc-rpol:statements/oc-rpol:statement/oc-rpol:conditions/oc-rpol:config/oc-rpol:install-protocol-eq" {
    description
      "Not-supported deviation.";
    deviate not-supported;
  }

  deviation "/oc-rpol:routing-policy/oc-rpol:policy-definitions/oc-rpol:policy-definition/oc-rpol:statements/oc-rpol:statement/oc-rpol:conditions/oc-rpol:state/oc-rpol:install-protocol-eq" {
    description
      "Not-supported deviation.";
    deviate not-supported;
  }
}
