module arista-acl-acl-open-config-icmpv4-types {
  yang-version 1;
  namespace "http://arista.com/yang/experimental/eos/arista-acl-acl-open-config-icmpv4-types";
  prefix "arista-acl-acl-open-config-icmpv4-types";
  
  import openconfig-extensions { prefix "oc-ext"; }
  import openconfig-icmpv4-types { prefix "openconfig-icmpv4-types"; }
  organization
    "Arista Networks <http://arista.com/>";
  contact
    "Arista Networks <http://arista.com/>";
  description
    "Identity types relating to icmpv4
    
    THIS YANG MODULE WAS GENERATED FROM /src/Acl/AclOpenConfigIcmpv4Types.tac.
    
    DO NOT EDIT THIS FILE.";
  
  oc-ext:openconfig-version "1.0.0";
  
  revision "2024-07-19" {
    description
      "Version 1.0.0, generated on 2024-07-19";
    reference "1.0.0";
  }
  
  // covered-by: openconfig-icmpv4-types.yang
} // main-yang
