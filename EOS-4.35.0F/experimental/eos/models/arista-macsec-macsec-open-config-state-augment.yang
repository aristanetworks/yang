module arista-macsec-macsec-open-config-state-augment {
  yang-version 1;
  namespace "http://arista.com/yang/experimental/eos/arista-macsec-macsec-open-config-state-augment";
  prefix "arista-macsec-macsec-open-config-state-augment";
  
  import openconfig-extensions { prefix "oc-ext"; }
  import openconfig-interfaces { prefix "openconfig-interfaces"; }
  import openconfig-macsec { prefix "openconfig-macsec"; }
  organization
    "Arista Networks <http://arista.com/>";
  contact
    "Arista Networks <http://arista.com/>";
  description
    "Arista augmentations model for macsec
    
    THIS YANG MODULE WAS GENERATED FROM /src/Macsec/MacsecOpenConfigSharkState.tac.
    
    DO NOT EDIT THIS FILE.";
  
  oc-ext:openconfig-version "1.0.0";
  
  revision "2025-02-25" {
    description
      "Version 1.0.0, generated on 2025-02-25";
    reference "1.0.0";
  }
  
  grouping macsec-ocmacsec-interface-mka-state-counter {
    leaf in-mkpdu-bad-peer-errors {
      type uint64;
      description
        "MKPDU RX bad peer message number error count.";
    }
    leaf in-mkpdu-icv-verification-errors {
      type uint64;
      description
        "MKPDU RX ICV verification error count.";
    }
    description
      "macsec-ocmacsec-interface-mka-state-counter";
  }
  
  augment "/openconfig-macsec:macsec/openconfig-macsec:interfaces/openconfig-macsec:interface/openconfig-macsec:mka/openconfig-macsec:state/openconfig-macsec:counters" {
    leaf in-mkpdu-bad-peer-errors {
      type uint64;
      description
        "MKPDU RX bad peer message number error count.";
    }
    leaf in-mkpdu-icv-verification-errors {
      type uint64;
      description
        "MKPDU RX ICV verification error count.";
    }
    description
      "";
  }
  grouping macsec-ocmacsec-interface-state-counter {
    leaf tx-toolong-pkts {
      type uint64;
      description
        "MACsec interface level Transmit Too Long Packets counter. This counter will increment if MACsec is enabled on the interface and packets get discarded during transmission because the packet length is greater than the MTU ( Maximum Transmission Unit ) set in the engine.";
    }
    leaf tx-ctrl-pkts {
      type uint64;
      description
        "MACsec interface level Transmit Control Packets counter. This counter represents all the control packets exiting the interface including MKPDUs, LLDP and any other control packets bypassed in MACsec.";
    }
    leaf rx-delayed-pkts {
      type uint64;
      description
        "MACsec interface level Receive Delayed Packets counter. This counter will increment if MACsec is enabled on the interface and the packet number of incoming packet is less than the lowest acceptable packet number and replay protection is disabled.";
    }
    leaf rx-ctrl-pkts {
      type uint64;
      description
        "MACsec interface level Receive Control Packets counter. This counter represents all the control packets entering the interface including MKPDUs, LLDP and any other control packets bypassed in MACsec.";
    }
    description
      "macsec-ocmacsec-interface-state-counter";
  }
  
  augment "/openconfig-macsec:macsec/openconfig-macsec:interfaces/openconfig-macsec:interface/openconfig-macsec:state/openconfig-macsec:counters" {
    leaf tx-toolong-pkts {
      type uint64;
      description
        "MACsec interface level Transmit Too Long Packets counter. This counter will increment if MACsec is enabled on the interface and packets get discarded during transmission because the packet length is greater than the MTU ( Maximum Transmission Unit ) set in the engine.";
    }
    leaf tx-ctrl-pkts {
      type uint64;
      description
        "MACsec interface level Transmit Control Packets counter. This counter represents all the control packets exiting the interface including MKPDUs, LLDP and any other control packets bypassed in MACsec.";
    }
    leaf rx-delayed-pkts {
      type uint64;
      description
        "MACsec interface level Receive Delayed Packets counter. This counter will increment if MACsec is enabled on the interface and the packet number of incoming packet is less than the lowest acceptable packet number and replay protection is disabled.";
    }
    leaf rx-ctrl-pkts {
      type uint64;
      description
        "MACsec interface level Receive Control Packets counter. This counter represents all the control packets entering the interface including MKPDUs, LLDP and any other control packets bypassed in MACsec.";
    }
    description
      "";
  }
  grouping macsec-ocmacsec-interface-state {
    leaf secured {
      type boolean;
      description
        "MACsec encryption status indicator. Set when MACsec is enabled on the interface and is exchanging encrypted traffic.";
    }
    description
      "macsec-ocmacsec-interface-state";
  }
  
  augment "/openconfig-macsec:macsec/openconfig-macsec:interfaces/openconfig-macsec:interface/openconfig-macsec:state" {
    leaf secured {
      type boolean;
      description
        "MACsec encryption status indicator. Set when MACsec is enabled on the interface and is exchanging encrypted traffic.";
    }
    description
      "";
  }
  grouping macsec-ocmacsec-interface-mka-state {
    description
      "macsec-ocmacsec-interface-mka-state";
  }
  
  grouping macsec-ocmacsec-interface-mka {
    description
      "macsec-ocmacsec-interface-mka";
  }
  
  grouping macsec-ocscsa-tx-counter {
    leaf sc-encrypted-octets {
      type uint64;
      description
        "Secure Channel Encrypted TX Octets counter. This counter reflects the number of encrypted and authenticated octets of transmitted packets in a secure channel.";
    }
    description
      "macsec-ocscsa-tx-counter";
  }
  
  augment "/openconfig-macsec:macsec/openconfig-macsec:interfaces/openconfig-macsec:interface/openconfig-macsec:scsa-tx/openconfig-macsec:scsa-tx/openconfig-macsec:state/openconfig-macsec:counters" {
    leaf sc-encrypted-octets {
      type uint64;
      description
        "Secure Channel Encrypted TX Octets counter. This counter reflects the number of encrypted and authenticated octets of transmitted packets in a secure channel.";
    }
    description
      "";
  }
  grouping macsec-ocscsa-tx-state {
    description
      "macsec-ocscsa-tx-state";
  }
  
  grouping macsec-ocscsa-tx-type {
    description
      "macsec-ocscsa-tx-type";
  }
  
  grouping macsec-ocscsa-tx {
    description
      "macsec-ocscsa-tx";
  }
  
  grouping macsec-ocscsa-rx-counter {
    leaf sc-valid-octets {
      type uint64;
      description
        "Valid Secure Channel RX Octets counter. This counter reflects the count of octets of valid received packets in a secure channel.";
    }
    description
      "macsec-ocscsa-rx-counter";
  }
  
  augment "/openconfig-macsec:macsec/openconfig-macsec:interfaces/openconfig-macsec:interface/openconfig-macsec:scsa-rx/openconfig-macsec:scsa-rx/openconfig-macsec:state/openconfig-macsec:counters" {
    leaf sc-valid-octets {
      type uint64;
      description
        "Valid Secure Channel RX Octets counter. This counter reflects the count of octets of valid received packets in a secure channel.";
    }
    description
      "";
  }
  grouping macsec-ocscsa-rx-state {
    description
      "macsec-ocscsa-rx-state";
  }
  
  grouping macsec-ocscsa-rx-type {
    description
      "macsec-ocscsa-rx-type";
  }
  
  grouping macsec-ocscsa-rx {
    description
      "macsec-ocscsa-rx";
  }
  
  grouping macsec-ocmacsec-interface {
    description
      "macsec-ocmacsec-interface";
  }
  
  grouping macsec-ocmacsec-interfaces {
    description
      "macsec-ocmacsec-interfaces";
  }
  
  grouping macsec-ocmacsec-mka-policy-state {
    description
      "macsec-ocmacsec-mka-policy-state";
  }
  
  grouping macsec-ocmacsec-mka-state-counter {
    description
      "macsec-ocmacsec-mka-state-counter";
  }
  
  grouping macsec-ocmacsec-mka-state {
    description
      "macsec-ocmacsec-mka-state";
  }
  
  grouping macsec-ocmacsec-mka-policy {
    description
      "macsec-ocmacsec-mka-policy";
  }
  
  grouping macsec-ocmacsec-mka-policies {
    description
      "macsec-ocmacsec-mka-policies";
  }
  
  grouping macsec-ocmacsec-mka {
    description
      "macsec-ocmacsec-mka";
  }
  
} // augmented-yang
