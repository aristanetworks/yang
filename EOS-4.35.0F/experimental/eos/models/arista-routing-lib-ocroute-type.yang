module arista-routing-lib-ocroute-type {
  yang-version 1;
  namespace "http://arista.com/yang/experimental/eos/arista-routing-lib-ocroute-type";
  prefix "arista-routing-lib-ocroute-type";
  
  import openconfig-extensions { prefix "oc-ext"; }
  import openconfig-policy-types { prefix "openconfig-policy-types"; }
  organization
    "Arista Networks <http://arista.com/>";
  contact
    "Arista Networks <http://arista.com/>";
  description
    "This is the model for OpenConfig route protocol types
    
    THIS YANG MODULE WAS GENERATED FROM /src/RoutingLib/OCRouteType.tac.
    
    DO NOT EDIT THIS FILE.";
  
  oc-ext:openconfig-version "1.0.0";
  
  revision "2025-05-06" {
    description
      "Version 1.0.0, generated on 2025-05-06";
    reference "1.0.0";
  }
  
  // covered-by: openconfig-policy-types.yang, arista-aft-augments.yang
} // main-yang
