module arista-strata-mmu-lib-strata-mmu-pool-open-config {
  yang-version 1;
  namespace "http://arista.com/yang/experimental/eos/arista-strata-mmu-lib-strata-mmu-pool-open-config";
  prefix "arista-strata-mmu-lib-strata-mmu-pool-open-config";
  
  import openconfig-extensions { prefix "oc-ext"; }
  import arista-ale-counters-open-config-specialized-counters { prefix "arista-ale-counters-open-config-specialized-counters"; }
  import openconfig-platform { prefix "openconfig-platform"; }
  organization
    "Arista Networks <http://arista.com/>";
  contact
    "Arista Networks <http://arista.com/>";
  description
    "Model for MMU Counters
    
    THIS YANG MODULE WAS GENERATED FROM /src/StrataMmuLib/StrataMmuPoolOpenConfig.tac.
    
    DO NOT EDIT THIS FILE.";
  
  oc-ext:openconfig-version "0.1.0";
  
  revision "2025-07-10" {
    description
      "Version 0.1.0, generated on 2025-07-10";
    reference "0.1.0";
  }
  
  grouping strata-central-open-config-mmu-mod-pool-status {
    leaf xpe {
      type uint8;
      description
        "MMU Ingress XPE key";
    }
    leaf admitted-pkts {
      type uint64;
      description
        "Packets admitted into MOD Pool";
    }
    leaf dropped-pkts {
      type uint64;
      description
        "Packets not admitted into MOD Pool";
    }
    leaf eligible-pkts {
      type uint64;
      description
        "Packets eligible for MOD Pool";
    }
    leaf total-occupancy {
      type uint64;
      description
        "Current MOD Pool occupancy (number of packets)";
    }
    leaf high-watermark {
      type uint64;
      description
        "MOD Pool peak usage (number of packets)";
    }
    description
      "strata-central-open-config-mmu-mod-pool-status";
  }
  
  grouping strata-central-open-config-open-config-mmu-counters-status {
    list xpe-mod-pool-status {
      key "xpe";
      uses strata-central-open-config-mmu-mod-pool-status;
      description
        "xpe-mod-pool-status";
    }
    description
      "strata-central-open-config-open-config-mmu-counters-status";
  }
  
  augment "/openconfig-platform:components/openconfig-platform:component/openconfig-platform:integrated-circuit/arista-ale-counters-open-config-specialized-counters:specialized-counters/arista-ale-counters-open-config-specialized-counters:vendor/arista-ale-counters-open-config-specialized-counters:arista" {
    container strata {
      list mmu {
        key "xpe";
        leaf xpe {
          type string;
          description
            "xpe leaf used as key for mmu list";
        }
        container mirror-on-drop {
          container state {
            config false;
            uses strata-central-open-config-mmu-mod-pool-status;
            description
              "state container";
          }
          description
            "mirror-on-drop container";
        }
        description
          "mmu list";
      }
      description
        "strata container";
    }
  }
} // main-yang
