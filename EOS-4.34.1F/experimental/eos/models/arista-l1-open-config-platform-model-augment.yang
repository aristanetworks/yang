module arista-l1-open-config-platform-model-augment {
  yang-version 1;
  namespace "http://arista.com/yang/experimental/eos/arista-l1-open-config-platform-model-augment";
  prefix "arista-l1-open-config-platform-model-augment";
  
  import openconfig-extensions { prefix "oc-ext"; }
  import openconfig-platform { prefix "openconfig-platform"; }
  import openconfig-platform-types { prefix "openconfig-platform-types"; }
  organization
    "Arista Networks <http://arista.com/>";
  contact
    "Arista Networks <http://arista.com/>";
  description
    "Attributes related to generic platform components
    
    THIS YANG MODULE WAS GENERATED FROM /src/L1OpenConfig/PlatformModel.tac.
    
    DO NOT EDIT THIS FILE.";
  
  oc-ext:openconfig-version "1.0.0";
  
  revision "2022-05-12" {
    description
      "Version 1.0.0, generated on 2022-05-12";
    reference "1.0.0";
  }
  
  grouping l1-open-config-xcvr-platform-state {
    leaf max-module-power {
      type binary {
        length 8;
      }
      description
        "maxModulePower";
    }
    description
      "Container for the state of the component";
  }
  
  augment "/openconfig-platform:components/openconfig-platform:component/openconfig-platform:state" {
    leaf max-module-power {
      type binary {
        length 8;
      }
      description
        "maxModulePower";
    }
    description
      "maxModulePower";
  }
  grouping l1-open-config-xcvr-platform {
    description
      "Container for the component attributes";
  }
  
} // augmented-yang
