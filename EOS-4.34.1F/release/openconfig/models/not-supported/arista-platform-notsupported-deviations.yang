module arista-platform-notsupported-deviations {
  namespace "http://arista.com/yang/openconfig/platform/notsupported-deviations";
  prefix arista-platform-notsupported-deviations;

  import openconfig-alarms {
    prefix oc-alarms;
  }
  import openconfig-hercules-platform {
    prefix herc-platform;
  }
  import openconfig-platform {
    prefix oc-platform;
  }
  import openconfig-platform-integrated-circuit {
    prefix oc-ic;
  }
  import openconfig-platform-linecard {
    prefix oc-linecard;
  }
  import openconfig-platform-pipeline-counters {
    prefix oc-ppc;
  }
  import openconfig-platform-psu {
    prefix oc-platform-psu;
  }
  import openconfig-platform-transceiver {
    prefix oc-transceiver;
  }
  import openconfig-terminal-device {
    prefix oc-opt-term;
  }

  organization
    "Arista Networks, Inc.";
  contact
    "Arista Networks, Inc.
     Product Support";
  description
    "This module contains OpenConfig platform deviations in Arista EOS.
     Copyright (c) 2020 Arista Networks, Inc. All rights reserved.";

  revision 2025-05-30 {
    description
      "Auto-generated not-supported deviations for unsupported paths";
  }

  deviation "/oc-platform:components/oc-platform:component/oc-platform:backplane" {
    description
      "Not-supported deviation.";
    deviate not-supported;
  }

  deviation "/oc-platform:components/oc-platform:component/oc-platform:storage" {
    description
      "Not-supported deviation.";
    deviate not-supported;
  }

  deviation "/oc-platform:components/oc-platform:component/oc-linecard:linecard/oc-linecard:config/herc-platform:slot-id" {
    description
      "Not-supported deviation.";
    deviate not-supported;
  }

  deviation "/oc-platform:components/oc-platform:component/oc-linecard:linecard/oc-linecard:utilization/oc-linecard:resources/oc-linecard:resource/oc-linecard:config/oc-linecard:used-threshold-upper" {
    description
      "Not-supported deviation.";
    deviate not-supported;
  }

  deviation "/oc-platform:components/oc-platform:component/oc-linecard:linecard/oc-linecard:utilization/oc-linecard:resources/oc-linecard:resource/oc-linecard:config/oc-linecard:used-threshold-upper-clear" {
    description
      "Not-supported deviation.";
    deviate not-supported;
  }

  deviation "/oc-platform:components/oc-platform:component/oc-opt-term:optical-channel/oc-opt-term:config/oc-opt-term:line-port" {
    description
      "Not-supported deviation.";
    deviate not-supported;
  }

  deviation "/oc-platform:components/oc-platform:component/oc-opt-term:optical-channel/oc-opt-term:state/oc-opt-term:group-id" {
    description
      "Not-supported deviation.";
    deviate not-supported;
  }

  deviation "/oc-platform:components/oc-platform:component/oc-opt-term:optical-channel/oc-opt-term:state/oc-opt-term:line-port" {
    description
      "Not-supported deviation.";
    deviate not-supported;
  }

  deviation "/oc-platform:components/oc-platform:component/oc-opt-term:optical-channel/oc-opt-term:state/oc-opt-term:modulation-error-ratio" {
    description
      "Not-supported deviation.";
    deviate not-supported;
  }

  deviation "/oc-platform:components/oc-platform:component/oc-opt-term:optical-channel/oc-opt-term:state/oc-opt-term:modulator-bias-x-phase" {
    description
      "Not-supported deviation.";
    deviate not-supported;
  }

  deviation "/oc-platform:components/oc-platform:component/oc-opt-term:optical-channel/oc-opt-term:state/oc-opt-term:modulator-bias-xi" {
    description
      "Not-supported deviation.";
    deviate not-supported;
  }

  deviation "/oc-platform:components/oc-platform:component/oc-opt-term:optical-channel/oc-opt-term:state/oc-opt-term:modulator-bias-xq" {
    description
      "Not-supported deviation.";
    deviate not-supported;
  }

  deviation "/oc-platform:components/oc-platform:component/oc-opt-term:optical-channel/oc-opt-term:state/oc-opt-term:modulator-bias-y-phase" {
    description
      "Not-supported deviation.";
    deviate not-supported;
  }

  deviation "/oc-platform:components/oc-platform:component/oc-opt-term:optical-channel/oc-opt-term:state/oc-opt-term:modulator-bias-yi" {
    description
      "Not-supported deviation.";
    deviate not-supported;
  }

  deviation "/oc-platform:components/oc-platform:component/oc-opt-term:optical-channel/oc-opt-term:state/oc-opt-term:modulator-bias-yq" {
    description
      "Not-supported deviation.";
    deviate not-supported;
  }

  deviation "/oc-platform:components/oc-platform:component/oc-opt-term:optical-channel/oc-opt-term:state/oc-opt-term:post-fec-ber" {
    description
      "Not-supported deviation.";
    deviate not-supported;
  }

  deviation "/oc-platform:components/oc-platform:component/oc-opt-term:optical-channel/oc-opt-term:state/oc-opt-term:carrier-frequency-offset/oc-opt-term:max-time" {
    description
      "Not-supported deviation.";
    deviate not-supported;
  }

  deviation "/oc-platform:components/oc-platform:component/oc-opt-term:optical-channel/oc-opt-term:state/oc-opt-term:carrier-frequency-offset/oc-opt-term:min-time" {
    description
      "Not-supported deviation.";
    deviate not-supported;
  }

  deviation "/oc-platform:components/oc-platform:component/oc-opt-term:optical-channel/oc-opt-term:state/oc-opt-term:chromatic-dispersion/oc-opt-term:max-time" {
    description
      "Not-supported deviation.";
    deviate not-supported;
  }

  deviation "/oc-platform:components/oc-platform:component/oc-opt-term:optical-channel/oc-opt-term:state/oc-opt-term:chromatic-dispersion/oc-opt-term:min-time" {
    description
      "Not-supported deviation.";
    deviate not-supported;
  }

  deviation "/oc-platform:components/oc-platform:component/oc-opt-term:optical-channel/oc-opt-term:state/oc-opt-term:esnr/oc-opt-term:max-time" {
    description
      "Not-supported deviation.";
    deviate not-supported;
  }

  deviation "/oc-platform:components/oc-platform:component/oc-opt-term:optical-channel/oc-opt-term:state/oc-opt-term:esnr/oc-opt-term:min-time" {
    description
      "Not-supported deviation.";
    deviate not-supported;
  }

  deviation "/oc-platform:components/oc-platform:component/oc-opt-term:optical-channel/oc-opt-term:state/oc-opt-term:input-power/oc-opt-term:max-time" {
    description
      "Not-supported deviation.";
    deviate not-supported;
  }

  deviation "/oc-platform:components/oc-platform:component/oc-opt-term:optical-channel/oc-opt-term:state/oc-opt-term:input-power/oc-opt-term:min-time" {
    description
      "Not-supported deviation.";
    deviate not-supported;
  }

  deviation "/oc-platform:components/oc-platform:component/oc-opt-term:optical-channel/oc-opt-term:state/oc-opt-term:laser-bias-current/oc-opt-term:avg" {
    description
      "Not-supported deviation.";
    deviate not-supported;
  }

  deviation "/oc-platform:components/oc-platform:component/oc-opt-term:optical-channel/oc-opt-term:state/oc-opt-term:laser-bias-current/oc-opt-term:interval" {
    description
      "Not-supported deviation.";
    deviate not-supported;
  }

  deviation "/oc-platform:components/oc-platform:component/oc-opt-term:optical-channel/oc-opt-term:state/oc-opt-term:laser-bias-current/oc-opt-term:max" {
    description
      "Not-supported deviation.";
    deviate not-supported;
  }

  deviation "/oc-platform:components/oc-platform:component/oc-opt-term:optical-channel/oc-opt-term:state/oc-opt-term:laser-bias-current/oc-opt-term:max-time" {
    description
      "Not-supported deviation.";
    deviate not-supported;
  }

  deviation "/oc-platform:components/oc-platform:component/oc-opt-term:optical-channel/oc-opt-term:state/oc-opt-term:laser-bias-current/oc-opt-term:min" {
    description
      "Not-supported deviation.";
    deviate not-supported;
  }

  deviation "/oc-platform:components/oc-platform:component/oc-opt-term:optical-channel/oc-opt-term:state/oc-opt-term:laser-bias-current/oc-opt-term:min-time" {
    description
      "Not-supported deviation.";
    deviate not-supported;
  }

  deviation "/oc-platform:components/oc-platform:component/oc-opt-term:optical-channel/oc-opt-term:state/oc-opt-term:osnr/oc-opt-term:max-time" {
    description
      "Not-supported deviation.";
    deviate not-supported;
  }

  deviation "/oc-platform:components/oc-platform:component/oc-opt-term:optical-channel/oc-opt-term:state/oc-opt-term:osnr/oc-opt-term:min-time" {
    description
      "Not-supported deviation.";
    deviate not-supported;
  }

  deviation "/oc-platform:components/oc-platform:component/oc-opt-term:optical-channel/oc-opt-term:state/oc-opt-term:output-power/oc-opt-term:max-time" {
    description
      "Not-supported deviation.";
    deviate not-supported;
  }

  deviation "/oc-platform:components/oc-platform:component/oc-opt-term:optical-channel/oc-opt-term:state/oc-opt-term:output-power/oc-opt-term:min-time" {
    description
      "Not-supported deviation.";
    deviate not-supported;
  }

  deviation "/oc-platform:components/oc-platform:component/oc-opt-term:optical-channel/oc-opt-term:state/oc-opt-term:polarization-dependent-loss/oc-opt-term:max-time" {
    description
      "Not-supported deviation.";
    deviate not-supported;
  }

  deviation "/oc-platform:components/oc-platform:component/oc-opt-term:optical-channel/oc-opt-term:state/oc-opt-term:polarization-dependent-loss/oc-opt-term:min-time" {
    description
      "Not-supported deviation.";
    deviate not-supported;
  }

  deviation "/oc-platform:components/oc-platform:component/oc-opt-term:optical-channel/oc-opt-term:state/oc-opt-term:polarization-mode-dispersion/oc-opt-term:max-time" {
    description
      "Not-supported deviation.";
    deviate not-supported;
  }

  deviation "/oc-platform:components/oc-platform:component/oc-opt-term:optical-channel/oc-opt-term:state/oc-opt-term:polarization-mode-dispersion/oc-opt-term:min-time" {
    description
      "Not-supported deviation.";
    deviate not-supported;
  }

  deviation "/oc-platform:components/oc-platform:component/oc-opt-term:optical-channel/oc-opt-term:state/oc-opt-term:pre-fec-ber/oc-opt-term:max-time" {
    description
      "Not-supported deviation.";
    deviate not-supported;
  }

  deviation "/oc-platform:components/oc-platform:component/oc-opt-term:optical-channel/oc-opt-term:state/oc-opt-term:pre-fec-ber/oc-opt-term:min-time" {
    description
      "Not-supported deviation.";
    deviate not-supported;
  }

  deviation "/oc-platform:components/oc-platform:component/oc-opt-term:optical-channel/oc-opt-term:state/oc-opt-term:q-value/oc-opt-term:max-time" {
    description
      "Not-supported deviation.";
    deviate not-supported;
  }

  deviation "/oc-platform:components/oc-platform:component/oc-opt-term:optical-channel/oc-opt-term:state/oc-opt-term:q-value/oc-opt-term:min-time" {
    description
      "Not-supported deviation.";
    deviate not-supported;
  }

  deviation "/oc-platform:components/oc-platform:component/oc-opt-term:optical-channel/oc-opt-term:state/oc-opt-term:second-order-polarization-mode-dispersion/oc-opt-term:max-time" {
    description
      "Not-supported deviation.";
    deviate not-supported;
  }

  deviation "/oc-platform:components/oc-platform:component/oc-opt-term:optical-channel/oc-opt-term:state/oc-opt-term:second-order-polarization-mode-dispersion/oc-opt-term:min-time" {
    description
      "Not-supported deviation.";
    deviate not-supported;
  }

  deviation "/oc-platform:components/oc-platform:component/oc-opt-term:optical-channel/oc-opt-term:state/oc-opt-term:sop-roc/oc-opt-term:max-time" {
    description
      "Not-supported deviation.";
    deviate not-supported;
  }

  deviation "/oc-platform:components/oc-platform:component/oc-opt-term:optical-channel/oc-opt-term:state/oc-opt-term:sop-roc/oc-opt-term:min-time" {
    description
      "Not-supported deviation.";
    deviate not-supported;
  }

  deviation "/oc-platform:components/oc-platform:component/oc-platform:chassis/oc-platform:config" {
    description
      "Not-supported deviation.";
    deviate not-supported;
  }

  deviation "/oc-platform:components/oc-platform:component/oc-platform:chassis/oc-platform:state" {
    description
      "Not-supported deviation.";
    deviate not-supported;
  }

  deviation "/oc-platform:components/oc-platform:component/oc-platform:chassis/herc-platform:alarms/herc-platform:critical-state/herc-platform:info" {
    description
      "Not-supported deviation.";
    deviate not-supported;
  }

  deviation "/oc-platform:components/oc-platform:component/oc-platform:chassis/oc-platform:utilization/oc-platform:resources/oc-platform:resource/oc-platform:config/oc-platform:used-threshold-upper" {
    description
      "Not-supported deviation.";
    deviate not-supported;
  }

  deviation "/oc-platform:components/oc-platform:component/oc-platform:chassis/oc-platform:utilization/oc-platform:resources/oc-platform:resource/oc-platform:config/oc-platform:used-threshold-upper-clear" {
    description
      "Not-supported deviation.";
    deviate not-supported;
  }

  deviation "/oc-platform:components/oc-platform:component/oc-platform:config/herc-platform:type" {
    description
      "Not-supported deviation.";
    deviate not-supported;
  }

  deviation "/oc-platform:components/oc-platform:component/oc-platform:cpu/oc-platform:config" {
    description
      "Not-supported deviation.";
    deviate not-supported;
  }

  deviation "/oc-platform:components/oc-platform:component/oc-platform:cpu/oc-platform:state" {
    description
      "Not-supported deviation.";
    deviate not-supported;
  }

  deviation "/oc-platform:components/oc-platform:component/oc-platform:fan/oc-platform:config" {
    description
      "Not-supported deviation.";
    deviate not-supported;
  }

  deviation "/oc-platform:components/oc-platform:component/oc-platform:integrated-circuit/herc-platform:vendor-data" {
    description
      "Not-supported deviation.";
    deviate not-supported;
  }

  deviation "/oc-platform:components/oc-platform:component/oc-platform:integrated-circuit/oc-ic:memory" {
    description
      "Not-supported deviation.";
    deviate not-supported;
  }

  deviation "/oc-platform:components/oc-platform:component/oc-platform:integrated-circuit/oc-platform:utilization/oc-platform:resources/oc-platform:resource/oc-platform:config/oc-platform:used-threshold-upper" {
    description
      "Not-supported deviation.";
    deviate not-supported;
  }

  deviation "/oc-platform:components/oc-platform:component/oc-platform:integrated-circuit/oc-platform:utilization/oc-platform:resources/oc-platform:resource/oc-platform:config/oc-platform:used-threshold-upper-clear" {
    description
      "Not-supported deviation.";
    deviate not-supported;
  }

  deviation "/oc-platform:components/oc-platform:component/oc-platform:integrated-circuit/oc-ppc:pipeline-counters/oc-ppc:drop/oc-ppc:state/oc-ppc:no-route" {
    description
      "Not-supported deviation.";
    deviate not-supported;
  }

  deviation "/oc-platform:components/oc-platform:component/oc-platform:integrated-circuit/oc-ppc:pipeline-counters/oc-ppc:drop/oc-ppc:state/oc-ppc:urpf-aggregate" {
    description
      "Not-supported deviation.";
    deviate not-supported;
  }

  deviation "/oc-platform:components/oc-platform:component/oc-platform:port/oc-platform:config" {
    description
      "Not-supported deviation.";
    deviate not-supported;
  }

  deviation "/oc-platform:components/oc-platform:component/oc-platform:port/oc-platform:state" {
    description
      "Not-supported deviation.";
    deviate not-supported;
  }

  deviation "/oc-platform:components/oc-platform:component/oc-platform:power-supply/oc-platform:config" {
    description
      "Not-supported deviation.";
    deviate not-supported;
  }

  deviation "/oc-platform:components/oc-platform:component/oc-platform:power-supply/oc-platform:state/oc-platform-psu:enabled" {
    description
      "Not-supported deviation.";
    deviate not-supported;
  }

  deviation "/oc-platform:components/oc-platform:component/oc-platform:properties/oc-platform:property/oc-platform:config/oc-platform:value" {
    description
      "Not-supported deviation.";
    deviate not-supported;
  }

  deviation "/oc-platform:components/oc-platform:component/oc-platform:properties/oc-platform:property/oc-platform:state/oc-platform:configurable" {
    description
      "Not-supported deviation.";
    deviate not-supported;
  }

  deviation "/oc-platform:components/oc-platform:component/oc-platform:software-module/oc-platform:config" {
    description
      "Not-supported deviation.";
    deviate not-supported;
  }

  deviation "/oc-platform:components/oc-platform:component/oc-platform:state/oc-alarms:equipment-failure" {
    description
      "Not-supported deviation.";
    deviate not-supported;
  }

  deviation "/oc-platform:components/oc-platform:component/oc-platform:state/oc-alarms:equipment-mismatch" {
    description
      "Not-supported deviation.";
    deviate not-supported;
  }

  deviation "/oc-platform:components/oc-platform:component/oc-platform:state/oc-platform:boot-time" {
    description
      "Not-supported deviation.";
    deviate not-supported;
  }

  deviation "/oc-platform:components/oc-platform:component/oc-platform:state/oc-platform:clei-code" {
    description
      "Not-supported deviation.";
    deviate not-supported;
  }

  deviation "/oc-platform:components/oc-platform:component/oc-platform:state/oc-platform:install-component" {
    description
      "Not-supported deviation.";
    deviate not-supported;
  }

  deviation "/oc-platform:components/oc-platform:component/oc-platform:state/oc-platform:install-position" {
    description
      "Not-supported deviation.";
    deviate not-supported;
  }

  deviation "/oc-platform:components/oc-platform:component/oc-platform:state/oc-platform:last-poweroff-reason" {
    description
      "Not-supported deviation.";
    deviate not-supported;
  }

  deviation "/oc-platform:components/oc-platform:component/oc-platform:state/oc-platform:last-poweroff-time" {
    description
      "Not-supported deviation.";
    deviate not-supported;
  }

  deviation "/oc-platform:components/oc-platform:component/oc-platform:state/oc-platform:model-name" {
    description
      "Not-supported deviation.";
    deviate not-supported;
  }

  deviation "/oc-platform:components/oc-platform:component/oc-platform:state/oc-platform:used-power" {
    description
      "Not-supported deviation.";
    deviate not-supported;
  }

  deviation "/oc-platform:components/oc-platform:component/oc-platform:state/oc-platform:temperature/oc-platform:avg" {
    description
      "Not-supported deviation.";
    deviate not-supported;
  }

  deviation "/oc-platform:components/oc-platform:component/oc-platform:state/oc-platform:temperature/oc-platform:interval" {
    description
      "Not-supported deviation.";
    deviate not-supported;
  }

  deviation "/oc-platform:components/oc-platform:component/oc-platform:state/oc-platform:temperature/oc-platform:min" {
    description
      "Not-supported deviation.";
    deviate not-supported;
  }

  deviation "/oc-platform:components/oc-platform:component/oc-platform:state/oc-platform:temperature/oc-platform:min-time" {
    description
      "Not-supported deviation.";
    deviate not-supported;
  }

  deviation "/oc-platform:components/oc-platform:component/oc-transceiver:transceiver/oc-transceiver:config/oc-transceiver:ethernet-pmd-preconf" {
    description
      "Not-supported deviation.";
    deviate not-supported;
  }

  deviation "/oc-platform:components/oc-platform:component/oc-transceiver:transceiver/oc-transceiver:config/oc-transceiver:fec-mode" {
    description
      "Not-supported deviation.";
    deviate not-supported;
  }

  deviation "/oc-platform:components/oc-platform:component/oc-transceiver:transceiver/oc-transceiver:config/oc-transceiver:form-factor-preconf" {
    description
      "Not-supported deviation.";
    deviate not-supported;
  }

  deviation "/oc-platform:components/oc-platform:component/oc-transceiver:transceiver/oc-transceiver:config/oc-transceiver:module-functional-type" {
    description
      "Not-supported deviation.";
    deviate not-supported;
  }

  deviation "/oc-platform:components/oc-platform:component/oc-transceiver:transceiver/oc-transceiver:physical-channels/oc-transceiver:channel/oc-transceiver:config/oc-transceiver:associated-optical-channel" {
    description
      "Not-supported deviation.";
    deviate not-supported;
  }

  deviation "/oc-platform:components/oc-platform:component/oc-transceiver:transceiver/oc-transceiver:physical-channels/oc-transceiver:channel/oc-transceiver:config/oc-transceiver:description" {
    description
      "Not-supported deviation.";
    deviate not-supported;
  }

  deviation "/oc-platform:components/oc-platform:component/oc-transceiver:transceiver/oc-transceiver:physical-channels/oc-transceiver:channel/oc-transceiver:config/oc-transceiver:target-output-power" {
    description
      "Not-supported deviation.";
    deviate not-supported;
  }

  deviation "/oc-platform:components/oc-platform:component/oc-transceiver:transceiver/oc-transceiver:physical-channels/oc-transceiver:channel/oc-transceiver:state/oc-transceiver:output-frequency" {
    description
      "Not-supported deviation.";
    deviate not-supported;
  }

  deviation "/oc-platform:components/oc-platform:component/oc-transceiver:transceiver/oc-transceiver:physical-channels/oc-transceiver:channel/oc-transceiver:state/oc-transceiver:target-output-power" {
    description
      "Not-supported deviation.";
    deviate not-supported;
  }

  deviation "/oc-platform:components/oc-platform:component/oc-transceiver:transceiver/oc-transceiver:physical-channels/oc-transceiver:channel/oc-transceiver:state/oc-transceiver:input-power/oc-transceiver:max-time" {
    description
      "Not-supported deviation.";
    deviate not-supported;
  }

  deviation "/oc-platform:components/oc-platform:component/oc-transceiver:transceiver/oc-transceiver:physical-channels/oc-transceiver:channel/oc-transceiver:state/oc-transceiver:input-power/oc-transceiver:min-time" {
    description
      "Not-supported deviation.";
    deviate not-supported;
  }

  deviation "/oc-platform:components/oc-platform:component/oc-transceiver:transceiver/oc-transceiver:physical-channels/oc-transceiver:channel/oc-transceiver:state/oc-transceiver:laser-bias-current/oc-transceiver:avg" {
    description
      "Not-supported deviation.";
    deviate not-supported;
  }

  deviation "/oc-platform:components/oc-platform:component/oc-transceiver:transceiver/oc-transceiver:physical-channels/oc-transceiver:channel/oc-transceiver:state/oc-transceiver:laser-bias-current/oc-transceiver:interval" {
    description
      "Not-supported deviation.";
    deviate not-supported;
  }

  deviation "/oc-platform:components/oc-platform:component/oc-transceiver:transceiver/oc-transceiver:physical-channels/oc-transceiver:channel/oc-transceiver:state/oc-transceiver:laser-bias-current/oc-transceiver:max" {
    description
      "Not-supported deviation.";
    deviate not-supported;
  }

  deviation "/oc-platform:components/oc-platform:component/oc-transceiver:transceiver/oc-transceiver:physical-channels/oc-transceiver:channel/oc-transceiver:state/oc-transceiver:laser-bias-current/oc-transceiver:max-time" {
    description
      "Not-supported deviation.";
    deviate not-supported;
  }

  deviation "/oc-platform:components/oc-platform:component/oc-transceiver:transceiver/oc-transceiver:physical-channels/oc-transceiver:channel/oc-transceiver:state/oc-transceiver:laser-bias-current/oc-transceiver:min" {
    description
      "Not-supported deviation.";
    deviate not-supported;
  }

  deviation "/oc-platform:components/oc-platform:component/oc-transceiver:transceiver/oc-transceiver:physical-channels/oc-transceiver:channel/oc-transceiver:state/oc-transceiver:laser-bias-current/oc-transceiver:min-time" {
    description
      "Not-supported deviation.";
    deviate not-supported;
  }

  deviation "/oc-platform:components/oc-platform:component/oc-transceiver:transceiver/oc-transceiver:physical-channels/oc-transceiver:channel/oc-transceiver:state/oc-transceiver:laser-temperature/oc-transceiver:avg" {
    description
      "Not-supported deviation.";
    deviate not-supported;
  }

  deviation "/oc-platform:components/oc-platform:component/oc-transceiver:transceiver/oc-transceiver:physical-channels/oc-transceiver:channel/oc-transceiver:state/oc-transceiver:laser-temperature/oc-transceiver:interval" {
    description
      "Not-supported deviation.";
    deviate not-supported;
  }

  deviation "/oc-platform:components/oc-platform:component/oc-transceiver:transceiver/oc-transceiver:physical-channels/oc-transceiver:channel/oc-transceiver:state/oc-transceiver:laser-temperature/oc-transceiver:max" {
    description
      "Not-supported deviation.";
    deviate not-supported;
  }

  deviation "/oc-platform:components/oc-platform:component/oc-transceiver:transceiver/oc-transceiver:physical-channels/oc-transceiver:channel/oc-transceiver:state/oc-transceiver:laser-temperature/oc-transceiver:max-time" {
    description
      "Not-supported deviation.";
    deviate not-supported;
  }

  deviation "/oc-platform:components/oc-platform:component/oc-transceiver:transceiver/oc-transceiver:physical-channels/oc-transceiver:channel/oc-transceiver:state/oc-transceiver:laser-temperature/oc-transceiver:min" {
    description
      "Not-supported deviation.";
    deviate not-supported;
  }

  deviation "/oc-platform:components/oc-platform:component/oc-transceiver:transceiver/oc-transceiver:physical-channels/oc-transceiver:channel/oc-transceiver:state/oc-transceiver:laser-temperature/oc-transceiver:min-time" {
    description
      "Not-supported deviation.";
    deviate not-supported;
  }

  deviation "/oc-platform:components/oc-platform:component/oc-transceiver:transceiver/oc-transceiver:physical-channels/oc-transceiver:channel/oc-transceiver:state/oc-transceiver:output-power/oc-transceiver:avg" {
    description
      "Not-supported deviation.";
    deviate not-supported;
  }

  deviation "/oc-platform:components/oc-platform:component/oc-transceiver:transceiver/oc-transceiver:physical-channels/oc-transceiver:channel/oc-transceiver:state/oc-transceiver:output-power/oc-transceiver:interval" {
    description
      "Not-supported deviation.";
    deviate not-supported;
  }

  deviation "/oc-platform:components/oc-platform:component/oc-transceiver:transceiver/oc-transceiver:physical-channels/oc-transceiver:channel/oc-transceiver:state/oc-transceiver:output-power/oc-transceiver:max" {
    description
      "Not-supported deviation.";
    deviate not-supported;
  }

  deviation "/oc-platform:components/oc-platform:component/oc-transceiver:transceiver/oc-transceiver:physical-channels/oc-transceiver:channel/oc-transceiver:state/oc-transceiver:output-power/oc-transceiver:max-time" {
    description
      "Not-supported deviation.";
    deviate not-supported;
  }

  deviation "/oc-platform:components/oc-platform:component/oc-transceiver:transceiver/oc-transceiver:physical-channels/oc-transceiver:channel/oc-transceiver:state/oc-transceiver:output-power/oc-transceiver:min" {
    description
      "Not-supported deviation.";
    deviate not-supported;
  }

  deviation "/oc-platform:components/oc-platform:component/oc-transceiver:transceiver/oc-transceiver:physical-channels/oc-transceiver:channel/oc-transceiver:state/oc-transceiver:output-power/oc-transceiver:min-time" {
    description
      "Not-supported deviation.";
    deviate not-supported;
  }

  deviation "/oc-platform:components/oc-platform:component/oc-transceiver:transceiver/oc-transceiver:physical-channels/oc-transceiver:channel/oc-transceiver:state/oc-transceiver:target-frequency-deviation/oc-transceiver:avg" {
    description
      "Not-supported deviation.";
    deviate not-supported;
  }

  deviation "/oc-platform:components/oc-platform:component/oc-transceiver:transceiver/oc-transceiver:physical-channels/oc-transceiver:channel/oc-transceiver:state/oc-transceiver:target-frequency-deviation/oc-transceiver:interval" {
    description
      "Not-supported deviation.";
    deviate not-supported;
  }

  deviation "/oc-platform:components/oc-platform:component/oc-transceiver:transceiver/oc-transceiver:physical-channels/oc-transceiver:channel/oc-transceiver:state/oc-transceiver:target-frequency-deviation/oc-transceiver:max" {
    description
      "Not-supported deviation.";
    deviate not-supported;
  }

  deviation "/oc-platform:components/oc-platform:component/oc-transceiver:transceiver/oc-transceiver:physical-channels/oc-transceiver:channel/oc-transceiver:state/oc-transceiver:target-frequency-deviation/oc-transceiver:max-time" {
    description
      "Not-supported deviation.";
    deviate not-supported;
  }

  deviation "/oc-platform:components/oc-platform:component/oc-transceiver:transceiver/oc-transceiver:physical-channels/oc-transceiver:channel/oc-transceiver:state/oc-transceiver:target-frequency-deviation/oc-transceiver:min" {
    description
      "Not-supported deviation.";
    deviate not-supported;
  }

  deviation "/oc-platform:components/oc-platform:component/oc-transceiver:transceiver/oc-transceiver:physical-channels/oc-transceiver:channel/oc-transceiver:state/oc-transceiver:target-frequency-deviation/oc-transceiver:min-time" {
    description
      "Not-supported deviation.";
    deviate not-supported;
  }

  deviation "/oc-platform:components/oc-platform:component/oc-transceiver:transceiver/oc-transceiver:physical-channels/oc-transceiver:channel/oc-transceiver:state/oc-transceiver:tec-current/oc-transceiver:avg" {
    description
      "Not-supported deviation.";
    deviate not-supported;
  }

  deviation "/oc-platform:components/oc-platform:component/oc-transceiver:transceiver/oc-transceiver:physical-channels/oc-transceiver:channel/oc-transceiver:state/oc-transceiver:tec-current/oc-transceiver:interval" {
    description
      "Not-supported deviation.";
    deviate not-supported;
  }

  deviation "/oc-platform:components/oc-platform:component/oc-transceiver:transceiver/oc-transceiver:physical-channels/oc-transceiver:channel/oc-transceiver:state/oc-transceiver:tec-current/oc-transceiver:max" {
    description
      "Not-supported deviation.";
    deviate not-supported;
  }

  deviation "/oc-platform:components/oc-platform:component/oc-transceiver:transceiver/oc-transceiver:physical-channels/oc-transceiver:channel/oc-transceiver:state/oc-transceiver:tec-current/oc-transceiver:max-time" {
    description
      "Not-supported deviation.";
    deviate not-supported;
  }

  deviation "/oc-platform:components/oc-platform:component/oc-transceiver:transceiver/oc-transceiver:physical-channels/oc-transceiver:channel/oc-transceiver:state/oc-transceiver:tec-current/oc-transceiver:min" {
    description
      "Not-supported deviation.";
    deviate not-supported;
  }

  deviation "/oc-platform:components/oc-platform:component/oc-transceiver:transceiver/oc-transceiver:physical-channels/oc-transceiver:channel/oc-transceiver:state/oc-transceiver:tec-current/oc-transceiver:min-time" {
    description
      "Not-supported deviation.";
    deviate not-supported;
  }

  deviation "/oc-platform:components/oc-platform:component/oc-transceiver:transceiver/oc-transceiver:state/oc-transceiver:ethernet-pmd-preconf" {
    description
      "Not-supported deviation.";
    deviate not-supported;
  }

  deviation "/oc-platform:components/oc-platform:component/oc-transceiver:transceiver/oc-transceiver:state/oc-transceiver:fault-condition" {
    description
      "Not-supported deviation.";
    deviate not-supported;
  }

  deviation "/oc-platform:components/oc-platform:component/oc-transceiver:transceiver/oc-transceiver:state/oc-transceiver:fec-corrected-bits" {
    description
      "Not-supported deviation.";
    deviate not-supported;
  }

  deviation "/oc-platform:components/oc-platform:component/oc-transceiver:transceiver/oc-transceiver:state/oc-transceiver:fec-corrected-bytes" {
    description
      "Not-supported deviation.";
    deviate not-supported;
  }

  deviation "/oc-platform:components/oc-platform:component/oc-transceiver:transceiver/oc-transceiver:state/oc-transceiver:fec-mode" {
    description
      "Not-supported deviation.";
    deviate not-supported;
  }

  deviation "/oc-platform:components/oc-platform:component/oc-transceiver:transceiver/oc-transceiver:state/oc-transceiver:fec-status" {
    description
      "Not-supported deviation.";
    deviate not-supported;
  }

  deviation "/oc-platform:components/oc-platform:component/oc-transceiver:transceiver/oc-transceiver:state/oc-transceiver:fec-uncorrectable-blocks" {
    description
      "Not-supported deviation.";
    deviate not-supported;
  }

  deviation "/oc-platform:components/oc-platform:component/oc-transceiver:transceiver/oc-transceiver:state/oc-transceiver:fec-uncorrectable-words" {
    description
      "Not-supported deviation.";
    deviate not-supported;
  }

  deviation "/oc-platform:components/oc-platform:component/oc-transceiver:transceiver/oc-transceiver:state/oc-transceiver:form-factor-preconf" {
    description
      "Not-supported deviation.";
    deviate not-supported;
  }

  deviation "/oc-platform:components/oc-platform:component/oc-transceiver:transceiver/oc-transceiver:state/oc-transceiver:input-power" {
    description
      "Not-supported deviation.";
    deviate not-supported;
  }

  deviation "/oc-platform:components/oc-platform:component/oc-transceiver:transceiver/oc-transceiver:state/oc-transceiver:laser-bias-current" {
    description
      "Not-supported deviation.";
    deviate not-supported;
  }

  deviation "/oc-platform:components/oc-platform:component/oc-transceiver:transceiver/oc-transceiver:state/oc-transceiver:module-functional-type" {
    description
      "Not-supported deviation.";
    deviate not-supported;
  }

  deviation "/oc-platform:components/oc-platform:component/oc-transceiver:transceiver/oc-transceiver:state/oc-transceiver:otn-compliance-code" {
    description
      "Not-supported deviation.";
    deviate not-supported;
  }

  deviation "/oc-platform:components/oc-platform:component/oc-transceiver:transceiver/oc-transceiver:state/oc-transceiver:output-power" {
    description
      "Not-supported deviation.";
    deviate not-supported;
  }

  deviation "/oc-platform:components/oc-platform:component/oc-transceiver:transceiver/oc-transceiver:state/oc-transceiver:post-fec-ber" {
    description
      "Not-supported deviation.";
    deviate not-supported;
  }

  deviation "/oc-platform:components/oc-platform:component/oc-transceiver:transceiver/oc-transceiver:state/oc-transceiver:pre-fec-ber" {
    description
      "Not-supported deviation.";
    deviate not-supported;
  }

  deviation "/oc-platform:components/oc-platform:component/oc-transceiver:transceiver/oc-transceiver:state/oc-transceiver:sonet-sdh-compliance-code" {
    description
      "Not-supported deviation.";
    deviate not-supported;
  }

  deviation "/oc-platform:components/oc-platform:component/oc-transceiver:transceiver/oc-transceiver:state/oc-transceiver:supply-voltage/oc-transceiver:avg" {
    description
      "Not-supported deviation.";
    deviate not-supported;
  }

  deviation "/oc-platform:components/oc-platform:component/oc-transceiver:transceiver/oc-transceiver:state/oc-transceiver:supply-voltage/oc-transceiver:interval" {
    description
      "Not-supported deviation.";
    deviate not-supported;
  }

  deviation "/oc-platform:components/oc-platform:component/oc-transceiver:transceiver/oc-transceiver:state/oc-transceiver:supply-voltage/oc-transceiver:max" {
    description
      "Not-supported deviation.";
    deviate not-supported;
  }

  deviation "/oc-platform:components/oc-platform:component/oc-transceiver:transceiver/oc-transceiver:state/oc-transceiver:supply-voltage/oc-transceiver:max-time" {
    description
      "Not-supported deviation.";
    deviate not-supported;
  }

  deviation "/oc-platform:components/oc-platform:component/oc-transceiver:transceiver/oc-transceiver:state/oc-transceiver:supply-voltage/oc-transceiver:min" {
    description
      "Not-supported deviation.";
    deviate not-supported;
  }

  deviation "/oc-platform:components/oc-platform:component/oc-transceiver:transceiver/oc-transceiver:state/oc-transceiver:supply-voltage/oc-transceiver:min-time" {
    description
      "Not-supported deviation.";
    deviate not-supported;
  }
}
