module arista-lacp-deviations {
  namespace "http://arista.com/yang/openconfig/lacp/deviations";
  prefix arista-lacp-deviations;

  import openconfig-lacp {
    prefix oc-lacp;
  }
  import openconfig-extensions {
    prefix oc-ext;
  }

  organization
    "Arista Networks, Inc.";
  contact
    "Arista Networks, Inc.
     Product Support";
  description
    "This module contains OpenConfig lacp deviations in Arista EOS.

     Copyright (c) 2017 Arista Networks, Inc. All rights reserved.";
  oc-ext:openconfig-version "1.1.3";

  revision 2022-02-04 {
    description
      "Remove deviation for leaf lacp-errors and lacp-unkown-errors";
    reference
      "1.1.3";
  }

  revision 2021-09-27 {
    description
      "pyang auto format";
    reference
      "1.1.2";
  }
  revision 2021-05-21 {
    description
      "Remove deviation for leaf lacp-mode.";
    reference
      "1.1.1";
  }
  revision 2021-03-05 {
    description
      "Remove deviation for leaf lacp-rx-errors.";
    reference
      "1.1.0";
  }
  revision 2020-11-30 {
    description
      "Fix errors reported by pyang.";
    reference
      "1.0.1";
  }
  revision 2017-09-07 {
    description
      "Initial deviations file.";
    reference
      "1.0.0";
  }

  deviation "/oc-lacp:lacp/oc-lacp:config/oc-lacp:system-priority" {
    description
      "system-priority has a default value of 0x8000 in EOS";
    deviate add {
      default "32768";
    }
  }

  deviation "/oc-lacp:lacp/oc-lacp:interfaces/oc-lacp:interface/oc-lacp:config/oc-lacp:system-priority" {
    description
      "EOS does not support port channel level system priority";
    deviate not-supported;
  }

  deviation "/oc-lacp:lacp/oc-lacp:interfaces/oc-lacp:interface/oc-lacp:state/oc-lacp:system-priority" {
    description
      "EOS does not support port channel level system priority";
    deviate not-supported;
  }

  deviation "/oc-lacp:lacp/oc-lacp:interfaces/oc-lacp:interface/oc-lacp:members/oc-lacp:member/oc-lacp:state/oc-lacp:counters/oc-lacp:lacp-tx-errors" {
    description
      "EOS does not support LACP TX errors";
    deviate not-supported;
  }
}
