module arista-bgp-augments {
  namespace "http://arista.com/yang/openconfig/bgp/augments";
  prefix arista-bgp-augments;

  import openconfig-network-instance {
    prefix oc-netinst;
  }
  import openconfig-routing-policy {
    prefix oc-rpol;
  }
  import openconfig-extensions {
    prefix oc-ext;
  }

  organization
    "Arista Networks, Inc.";
  contact
    "Arista Networks, Inc.
     Product Support";
  description
    "This module contains OpenConfig BGP deviations in Arista EOS.

     Copyright (c) 2019 Arista Networks, Inc. All rights reserved.";
  oc-ext:openconfig-version "2.0.1";

  revision 2020-11-30 {
    description
      "Fix errors reported by pyang.";
    reference
      "2.0.1";
  }
  revision 2020-05-27 {
    description
      "Changed the route-target import/export policies to be single leafrefs.";
    reference
      "2.0.0";
  }
  revision 2020-05-20 {
    description
      "Included export-imported-route for each VPN type.";
    reference
      "1.2.1";
  }
  revision 2020-03-03 {
    description
      "Added route-target information.";
    reference
      "1.1.1";
  }
  revision 2019-11-12 {
    description
      "Removed unneeded EVPN reference.";
    reference
      "1.0.1";
  }
  revision 2019-03-15 {
    description
      "Initial Augments file.";
    reference
      "1.0.0";
  }

  typedef route-target-type {
    type union {
      type string {
        pattern '(6553[0-5]|655[0-2][0-9]|654[0-9]{2}|65[0-4][0-9]{2}'
              + '|6[0-4][0-9]{3}|[1-5][0-9]{4}|[1-9][0-9]{1,3}|[0-9]):'
              + '(429496729[0-5]|42949672[0-8][0-9]|4294967[0-1][0-9]{2}'
              + '|429496[0-6][0-9]{3}|42949[0-5][0-9]{4}|4294[0-8][0-9]{5}|'
              + '429[0-3][0-9]{6}|4[0-1][0-9]{7}|[1-3][0-9]{9}|'
              + '[1-9][0-9]{1,8}|[0-9])';
      }
      type string {
        pattern '(([0-9]|[1-9][0-9]|1[0-9][0-9]|2[0-4][0-9]|'
              + '25[0-5])\.){3}([0-9]|[1-9][0-9]|1[0-9][0-9]|'
              + '2[0-4][0-9]|25[0-5]):'
              + '(6553[0-5]|655[0-2][0-9]|654[0-9]{2}|65[0-4][0-9]{2}'
              + '|6[0-4][0-9]{3}|[1-5][0-9]{4}|[1-9][0-9]{1,3}|[0-9])';
      }
      type string {
        pattern '(429496729[0-5]|42949672[0-8][0-9]|4294967[0-1][0-9]{2}'
              + '|429496[0-6][0-9]{3}|42949[0-5][0-9]{4}|4294[0-8][0-9]{5}|'
              + '429[0-3][0-9]{6}|4[0-1][0-9]{7}|[1-3][0-9]{9}|'
              + '[1-9][0-9]{1,8}|[0-9]):'
              + '(6553[0-5]|655[0-2][0-9]|654[0-9]{2}|65[0-4][0-9]{2}'
              + '|6[0-4][0-9]{3}|[1-5][0-9]{4}|[1-9][0-9]{1,3}|[0-9])';
      }
    }
    description
      "This is a subset of oc-bgp-types:bgp-ext-community-type for
       route-targets:
        - <2b AS>:<4b value> per RFC4360 section 4
        - <4b IPv4>:<2b value> per RFC4360 section 4
        - <4b AS>:<2b value> per RFC5668 section 4";
  }

  grouping route-target-config {
    description
      "Route-target configuration.";
    leaf-list import-target {
      type route-target-type;
      description
        "Import route-targets.";
    }
    leaf-list export-target {
      type route-target-type;
      description
        "Export route-targets.";
    }
    leaf import-policy {
      type leafref {
        path "/oc-rpol:routing-policy/oc-rpol:policy-definitions/"
           + "oc-rpol:policy-definition/oc-rpol:name";
      }
      description
        "Import routing policy.";
    }
    leaf export-policy {
      type leafref {
        path "/oc-rpol:routing-policy/oc-rpol:policy-definitions/"
           + "oc-rpol:policy-definition/oc-rpol:name";
      }
      description
        "Export routing policy.";
    }
    leaf export-imported-route {
      type boolean;
      description
        "Export imported routes.";
    }
  }

  grouping best-paths-counters {
    description
      "Peer/afi-safi best path counters.";
    leaf best-paths {
      type uint32;
      description
        "The number of best-paths advertised by the neighbor";
    }
    leaf best-ecmp-paths {
      type uint32;
      description
        "The number of best-ecmp-paths advertised by the neighbor";
    }
  }

  augment "/oc-netinst:network-instances/oc-netinst:network-instance/oc-netinst:protocols/oc-netinst:protocol"
        + "/oc-netinst:bgp/oc-netinst:global" {
    description
      "Augment the BGP global config to include route-target information";
    container evpn {
      description
        "EVPN route target configuration.";
      uses route-target-config;
    }
    container vpn-ipv4 {
      description
        "VPN IPv4 route target configuration.";
      uses route-target-config;
    }
    container vpn-ipv6 {
      description
        "VPN IPv6 route target configuration.";
      uses route-target-config;
    }
  }

  augment "/oc-netinst:network-instances/oc-netinst:network-instance/oc-netinst:protocols/oc-netinst:protocol"
        + "/oc-netinst:bgp/oc-netinst:neighbors/oc-netinst:neighbor/oc-netinst:afi-safis/oc-netinst:afi-safi"
        + "/oc-netinst:state/oc-netinst:prefixes" {
    description
      "Augment BGP neighbor model to support per peer/afi-safi best path counters";
    uses best-paths-counters;
  }
}
