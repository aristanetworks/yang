module arista-interfaces-rates {
  yang-version "1";

  namespace "http://arista.com/yang/experimental/eos/arista-interfaces-rates";
  prefix "oc-if-rates";
  
  import openconfig-extensions { prefix oc-ext; }
  import openconfig-types { prefix "oc-types"; }
  import openconfig-interfaces { prefix "oc-if"; }

  organization
    "Arista Networks <http://arista.com/>";

  contact
    "Arista Networks, Inc.
     Product Support";

  description
    "This module contains OpenConfig interface rates.
     Copyright (c) 2023 Arista Networks, Inc. All rights reserved.";

  oc-ext:openconfig-version "0.1.0";

  revision 2023-09-15 {
    description
      "Augment of /interfaces/interface to include interface rates.";
    reference
      "1.0.0";
  }

  grouping interface-rates-state {
     leaf out-bits-rate {
      type oc-types:ieeefloat32;
      units "bps";
      description
        "The calculated transmitted rate of the interface, measured in bits
        per second.";
    }

    leaf in-bits-rate {
      type oc-types:ieeefloat32;
      units "bps";
      description
        "The calculate received rate of the interface, measured in bits
        per second.";
    }

    leaf out-pkts-rate {
      type oc-types:ieeefloat32;
      units "bps";
      description
        "The calculated transmitted rate of the interface, measured in packets
        per second.";
    }

    leaf in-pkts-rate {
      type oc-types:ieeefloat32;
      units "bps";
      description
        "The calculate received rate of the interface, measured in packets
        per second.";
    }
  }

  augment "/oc-if:interfaces/oc-if:interface" {
    container rates {
      description
        "Interfaces rates.";
      container state {
            config false;
            description
               "Operational state representing interface rates";
            uses interface-rates-state;
      }
    }
  }
}
