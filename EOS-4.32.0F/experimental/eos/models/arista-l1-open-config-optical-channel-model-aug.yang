module arista-l1-open-config-optical-channel-model-aug {
  yang-version 1;
  namespace "http://arista.com/yang/experimental/eos/arista-l1-open-config-optical-channel-model-aug";
  prefix "arista-l1-open-config-optical-channel-model-aug";

  import openconfig-extensions { prefix "oc-ext"; }
  import openconfig-platform { prefix "openconfig-platform"; }
  import openconfig-terminal-device { prefix "openconfig-terminal-device"; }
  organization
    "Arista Networks <http://arista.com/>";
  contact
    "Arista Networks <http://arista.com/>";
  description
    "Attributes related to optical parameters

    THIS YANG MODULE WAS GENERATED. DO NOT EDIT THIS FILE.";

  oc-ext:openconfig-version "1.0.0";

  revision "2022-05-12" {
    description
      "Version 1.0.0, generated on 2022-05-12";
    reference "1.0.0";
  }

  grouping opt-state-aug {
    leaf component-name {
      type string;
      description
        "Component name";
    }
    description
      "Augments for optical channel state attributes";
  }
  grouping optical-channel-aug {
    list state {
      key "component-name";
      uses opt-state-aug;
      description
        "Augments for the current state of the optical
          channel attributes";
    }
    leaf name {
      type string;
      description
        "name of the grouping";
    }
    description
      "Container for augmented optical channel states";
  }
  augment "/openconfig-platform:components/openconfig-platform:component/openconfig-terminal-device:optical-channel/openconfig-terminal-device:state" {
    uses opt-state-aug;
    description
      "/openconfig-platform:components/openconfig-platform:component/openconfig-terminal-device:optical-channel/openconfig-terminal-device:state augment";
  }
}
