module arista-messages-notsupported-deviations {
  namespace "http://arista.com/yang/openconfig/messages/notsupported-deviations";
  prefix arista-messages-notsupported-deviations;

  import openconfig-messages {
    prefix oc-messages;
  }

  organization
    "Arista Networks, Inc.";
  contact
    "Arista Networks, Inc.
     Product Support";
  description
    "This module contains OpenConfig messages deviations in Arista EOS.
     Copyright (c) 2020 Arista Networks, Inc. All rights reserved.";

  revision 2023-12-05 {
    description
      "Auto-generated not-supported deviations for unsupported paths";
  }

  deviation "/oc-messages:messages" {
    description
      "Not-supported deviation.";
    deviate not-supported;
  }
}
