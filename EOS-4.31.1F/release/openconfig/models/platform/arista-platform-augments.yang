module arista-platform-augments {

  yang-version "1";

  namespace "http://arista.com/yang/openconfig/platform/augments";

  prefix "arista-platform-augments";

  import openconfig-extensions { prefix oc-ext; }
  import openconfig-platform-pipeline-counters { prefix oc-ppc; }
  import openconfig-platform { prefix oc-platform; }

  organization
    "Arista Networks <http://arista.com/>";

  contact
    "Arista Networks, Inc.
     Product Support";

  description
    "This module contains OpenConfig platform pipeline counter augments in Arista EOS.

     Copyright (c) 2022 Arista Networks, Inc. All rights reserved.";

  oc-ext:openconfig-version "1.0.0";

  revision 2022-11-10 {
    description
      "Augment pipeline vendor drop counters with Arista and Sand specific container";
    reference
      "1.0.0";
  }

  augment "/oc-platform:components/oc-platform:component/oc-platform:integrated-circuit/oc-ppc:pipeline-counters/oc-ppc:drop/oc-ppc:vendor" {
	 description
		"Augment for Arista-specific drop counters";

    container arista {
		description
			"Container for Arista-specific drop counters";

      container sand {
		  description
		    "Container for Sand specific drop counters";

        uses oc-ppc:pipeline-vendor-drop-containers;
      }
    }
  }
}
