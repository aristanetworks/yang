module arista-aft-augments {
  namespace "http://arista.com/yang/openconfig/aft/augments";
  prefix arista-aft-augments;

  import openconfig-network-instance {
    prefix oc-netinst;
  }
  import openconfig-extensions {
    prefix oc-ext;
  }

  import openconfig-policy-types {
    prefix oc-pol-types;
  }

  organization
    "Arista Networks, Inc.";
  contact
    "Arista Networks, Inc.
     Product Support";
  description
    "This module contains OpenConfig AFT augments in Arista EOS.

     Copyright (c) 2019 Arista Networks, Inc. All rights reserved.";
  oc-ext:openconfig-version "1.0.1";

  revision 2023-08-24 {
    description
      "Add gre and mpls containers under next-hops aft entry state.
       Add ttl and tos under gre, mpls and ip-in-ip aft entry
       state for telemetry";
    reference
      "1.7.0";
  }

  revision 2023-07-11 {
    description
      "Add auto-size to next-hop-group state";
    reference
      "1.6.2";
  }

  revision 2023-05-23 {
    description
      "Add nexthop-group-name to next-hop-group state and
       ttl, tos to next-hop state.";
    reference
      "1.6.1";
  }

  revision 2022-02-03 {
    description
      "Remove INSTALL_PROTOCOL_TYPE gRIBI.";
    reference
      "1.6.1";
  }

  revision 2021-11-16 {
    description
      "Add more INSTALL_PROTOCOL_TYPE.";
    reference
      "1.6.1";
  }

  revision 2020-11-30 {
    description
      "Fix errors reported by pyang.";
    reference
      "1.0.1";
  }
  revision 2019-10-01 {
    description
      "Initial augment file.";
    reference
      "1.0.0";
  }

  grouping nexthop-counter-summary {
    description
      "Statistics for ECMP nexthops";
    leaf nexthop-ecmp-max-entries {
      type uint32;
      description
        "The maximum supported number of ECMP nexthop entries.";
    }
    leaf nexthop-ecmp-max-sets {
      type uint32;
      description
        "The maximum supported number of ECMP nexthop sets.";
    }
    leaf nexthop-ecmp-entries {
      type uint32;
      description
        "The number of currently used ECMP nexthop entries.";
    }
    leaf nexthop-ecmp-sets {
      type uint32;
      description
        "The number of currently used ECMP nexthop sets.";
    }
    leaf nexthop-ecmp-overlay-max-entries {
      type uint32;
      description
        "The maximum supported number of ECMP (overlay) nexthop entries.";
    }
    leaf nexthop-ecmp-overlay-max-sets {
      type uint32;
      description
        "The maximum supported number of ECMP (overlay) nexthop sets.";
    }
    leaf nexthop-ecmp-overlay-entries {
      type uint32;
      description
        "The number of currently used ECMP (overlay) nexthop entries.";
    }
    leaf nexthop-ecmp-overlay-sets {
      type uint32;
      description
        "The number of currently used ECMP (overlay) nexthop sets.";
    }
    leaf nexthop-ecmp-underlay-max-entries {
      type uint32;
      description
        "The maximum supported number of ECMP (underlay) nexthop entries.";
    }
    leaf nexthop-ecmp-underlay-max-sets {
      type uint32;
      description
        "The maximum supported number of ECMP (underlay) nexthop sets.";
    }
    leaf nexthop-ecmp-underlay-entries {
      type uint32;
      description
        "The number of currently used ECMP (underlay) nexthop entries.";
    }
    leaf nexthop-ecmp-underlay-sets {
      type uint32;
      description
        "The number of currently used ECMP (underlay) nexthop sets.";
    }
  }

  grouping aft-common-entry-nexthop-encap-outer-header-state {
    description
      "Outer header fields of encapsulation applied on a next-hop";
    leaf ttl {
      type uint8;
      description
        "This leaf reflects the configured/default TTL value that is used in the
         outer header during packet encapsulation. When this leaf is not set,
         the TTL value of the inner packet is copied over as the outer packet's
         TTL value during encapsulation.";
    }
    leaf tos {
      type uint8;
      description
        "This leaf reflects the configured/default TOS value that is used in the
         outer header during packet encapsulation. When this leaf is not set,
         the TOS value of the inner packet is copied over as the outer packet's
         TOS value during encapsulation.";
    }
  }

  augment "/oc-netinst:network-instances/oc-netinst:network-instance/oc-netinst:afts" {
    container nexthop-ecmp-counters {
      description
        "Statistics for ECMP nexthops";
      container state {
        config false;
        description
          "State parameters for ECMP nexthops";
        uses nexthop-counter-summary;
      }
    }
    description
      "Add Statistics for ECMP nexthops.";
  }

  augment
    "/oc-netinst:network-instances/oc-netinst:network-instance/oc-netinst:afts/"
  + "oc-netinst:next-hop-groups/oc-netinst:next-hop-group/oc-netinst:state" {
    description
      "This adds next-hop-group-name and auto-size to next-hop-group";

    leaf next-hop-group-name {
      type string;
      description
        "unique string name identifier for the nexthop-group";
    }

    leaf auto-size {
      type boolean;
      description
        "The indicator of the next-hop-group size being configured or
         automatically determined";
    }
  }

  augment
    "/oc-netinst:network-instances/oc-netinst:network-instance/oc-netinst:afts/"
  + "oc-netinst:next-hops/oc-netinst:next-hop/oc-netinst:ip-in-ip/"
  + "oc-netinst:state" {
    description
      "This adds ttl and tos to next-hop to ip-in-ip aft entry state";
    uses aft-common-entry-nexthop-encap-outer-header-state;
  }

  augment
    "/oc-netinst:network-instances/oc-netinst:network-instance/oc-netinst:afts/"
  + "oc-netinst:next-hops/oc-netinst:next-hop" {
    container gre {
      description
        "When specified, the packet has an GRE header applied to it before
         forwarding to the specified next-hop.";
      container state {
        config false;
        description
          "State parameters relating to GRE encapsulation.";
        uses aft-common-entry-nexthop-encap-outer-header-state;
      }
    }
    description
      "Add gre containers under next-hops aft entry state.
       Add ttl and tos under gre aft entry state for telemetry.";
  }

  augment
    "/oc-netinst:network-instances/oc-netinst:network-instance/oc-netinst:afts/"
  + "oc-netinst:next-hops/oc-netinst:next-hop" {
    container mpls {
      description
        "When specified, the packet has an MPLS header applied to it before
         forwarding to the specified next-hop.";
      container state {
        config false;
        description
          "State parameters relating to MPLS encapsulation.";
        uses aft-common-entry-nexthop-encap-outer-header-state;
      }
    }
    description
      "Add mpls containers under next-hops aft entry state.
       Add ttl and tos under mpls aft entry state for telemetry.";
  }

  identity ATTACHED {
    base oc-pol-types:INSTALL_PROTOCOL_TYPE;
    description "Attached route";
  }

  identity DHCP_DEFAULT_ROUTE {
    base oc-pol-types:INSTALL_PROTOCOL_TYPE;
    description "DHCP default route";
  }

  identity DYNAMIC_POLICY {
    base oc-pol-types:INSTALL_PROTOCOL_TYPE;
    description "Dynamic Policy";
  }

  identity L2_NEXT_HOP_GROUP {
    base oc-pol-types:INSTALL_PROTOCOL_TYPE;
    description "Layer2 Nexthop Group";
  }

  identity STATIC_NEXT_HOP_GROUP {
    base oc-pol-types:INSTALL_PROTOCOL_TYPE;
    description "Static Nexthop Group";
  }

  identity POLICY {
    base oc-pol-types:INSTALL_PROTOCOL_TYPE;
    description "Policy";
  }

  identity RIP {
    base oc-pol-types:INSTALL_PROTOCOL_TYPE;
    description "RIP";
    reference "RFC 2453";
  }

  identity ROUTE_CACHE_CONNECTED {
    base oc-pol-types:INSTALL_PROTOCOL_TYPE;
    description "Route Cache Connect";
  }

  identity ROUTE_CACHE_FORWARD {
    base oc-pol-types:INSTALL_PROTOCOL_TYPE;
    description "Route Cache Forward";
  }

  identity UNKNOWN {
    base oc-pol-types:INSTALL_PROTOCOL_TYPE;
    description "Unknown";
  }

  identity VCS {
    base oc-pol-types:INSTALL_PROTOCOL_TYPE;
    description "Vxlan Control Service";
  }

  identity INTERNAL {
    base oc-pol-types:INSTALL_PROTOCOL_TYPE;
    description "Internal";
  }
}
