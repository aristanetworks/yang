module arista-ale-counters-open-config-data-plane-traffic-policy-counters {
  yang-version 1;
  namespace "http://arista.com/yang/experimental/eos/arista-ale-counters-open-config-data-plane-traffic-policy-counters";
  prefix "arista-ale-counters-open-config-data-plane-traffic-policy-counters";

  import openconfig-extensions { prefix "oc-ext"; }
  import arista-exp-eos { prefix "arista-exp-eos"; }
  import arista-traffic-policy { prefix "arista-traffic-policy"; }
  organization
    "Arista Networks <http://arista.com/>";
  contact
    "Arista Networks <http://arista.com/>";
  description
    "Interface traffic policy counters

    THIS YANG MODULE WAS GENERATED. DO NOT EDIT THIS FILE.";

  oc-ext:openconfig-version "1.0.2";

  revision "2024-03-15" {
    description
      "Version 1.0.2, generated on 2024-03-15";
    reference "1.0.2";
  }

  // covered-by: arista-traffic-policy.yang
  grouping traffic-policy-counter-key {
    leaf policy-name {
      type string;
      description
        "internal implementation - please ignore";
    }
    leaf name {
      type string;
      description
        "Name of the counter";
    }
    description
      "Container for Conter key";
  }
  grouping traffic-policy-counter-data {
    uses traffic-policy-counter-key;
    leaf matched-packets {
      type uint64;
      description
        "Number of packets matched";
    }
    leaf dropped-packets {
      type uint64;
      description
        "Number of packets dropped";
    }
    leaf matched-octets {
      type uint64;
      description
        "Number of octets matched";
    }
    leaf dropped-octets {
      type uint64;
      description
        "Number of octets dropped";
    }
    description
      "Container for counters";
  }
  grouping data-plane-traffic-policy-egress {
    list counter {
      key "policy-name name";
      uses traffic-policy-counter-data;
      description
        "unused";
    }
    leaf name {
      type string;
      description
        "name of the grouping";
    }
    description
      "unused";
  }
  grouping data-plane-traffic-policy-ingress {
    list counter {
      key "policy-name name";
      uses traffic-policy-counter-data;
      description
        "unused";
    }
    leaf name {
      type string;
      description
        "name of the grouping";
    }
    description
      "unused";
  }
  augment "/arista-exp-eos:arista/arista-traffic-policy:traffic-policy" {
  container policies {
    list policy {
      key "name";
      leaf name {
        type string;
        description
          "name leaf used as key for policy list";
      }
      container data-plane-egress-counters {
        list counter {
          key "name";
          leaf name {
            type string;
            description
              "name leaf used as key for counter list";
          }
          container state {
            config false;
     uses traffic-policy-counter-data;
     description
         "state container";
      }
        description
         "counter list";
      }
        description
         "data-plane-egress-counters container";
      }
               container data-plane-ingress-counters {
              list counter {
                key "name";
                leaf name {
                  type string;
                  description
                    "name leaf used as key for counter list";
                }
                container state {
                  config false;
     uses traffic-policy-counter-data;
     description
         "state container";
      }
        description
         "counter list";
      }
        description
         "data-plane-ingress-counters container";
      }
        description
         "policy list";
      }
        description
         "policies container";
      }
   }
}
