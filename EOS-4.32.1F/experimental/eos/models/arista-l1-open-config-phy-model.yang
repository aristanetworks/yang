module arista-l1-open-config-phy-model {
  yang-version 1;
  namespace "http://arista.com/yang/experimental/eos/arista-l1-open-config-phy-model";
  prefix "arista-l1-open-config-phy-model";

  import openconfig-extensions { prefix "oc-ext"; }
  import openconfig-if-ethernet { prefix "openconfig-if-ethernet"; }
  import openconfig-interfaces { prefix "openconfig-interfaces"; }
  organization
    "Arista Networks <http://arista.com/>";
  contact
    "Arista Networks <http://arista.com/>";
  description
    "Attributes related to interface phy components

    THIS YANG MODULE WAS GENERATED. DO NOT EDIT THIS FILE.";

  oc-ext:openconfig-version "1.0.0";

  revision "2023-12-05" {
    description
      "Version 1.0.0, generated on 2023-12-05";
    reference "1.0.0";
  }

  grouping intf-phy-lane-index {
    leaf intf-name {
      type string;
      description
        "The interface name (eg, EthernetX/Y)";
    }
    leaf phy-index {
      type uint16;
      description
        "The index of the phy (0 is the phy in the ASIC)";
    }
    leaf lane {
      type uint16;
      description
        "The lane number (0 based)";
    }
    description
      "Index for a lane based phy attribute";
  }
  grouping pcs-lane-state {
    uses intf-phy-lane-index;
    leaf block-lock {
      type boolean;
      description
        "blockLock";
    }
    description
      "Lane based attributes for the physical coding sublayer";
  }
  grouping pcs-lane-ingress-container {
    list state {
      key "intf-name phy-index lane";
      uses pcs-lane-state;
      description
        "The lane based ingress state container for pcs";
    }
    leaf name {
      type string;
      description
        "name of the grouping";
    }
    description
      "Container for the ingress pcs lane component";
  }
  grouping pcs-lane-egress-container {
    list state {
      key "intf-name phy-index lane";
      uses pcs-lane-state;
      description
        "The lane based egress state container for pcs";
    }
    leaf name {
      type string;
      description
        "name of the grouping";
    }
    description
      "Container for the egress pcs lane component";
  }
  augment "/openconfig-interfaces:interfaces/openconfig-interfaces:interface/openconfig-if-ethernet:ethernet" {
  container phys {
    list phy {
      key "index";
      leaf index {
        type string;
        description
          "index leaf used as key for phy list";
      }
      container ingress {
        container pcs {
          container lanes {
            list lane {
              key "lane";
              leaf lane {
                type string;
                description
                  "lane leaf used as key for lane list";
              }
              container state {
                config false;
     uses pcs-lane-state;
     description
         "state container";
      }
        description
         "lane list";
      }
        description
         "lanes container";
      }
        description
         "pcs container";
      }
        description
         "ingress container";
      }
                   container egress {
                  container pcs {
                    container lanes {
                      list lane {
                        key "lane";
                        leaf lane {
                          type string;
                          description
                            "lane leaf used as key for lane list";
                        }
                        container state {
                          config false;
     uses pcs-lane-state;
     description
         "state container";
      }
        description
         "lane list";
      }
        description
         "lanes container";
      }
        description
         "pcs container";
      }
        description
         "egress container";
      }
        description
         "phy list";
      }
        description
         "phys container";
      }
   }
}
