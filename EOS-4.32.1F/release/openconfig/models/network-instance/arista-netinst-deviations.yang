module arista-netinst-deviations {
  namespace "http://arista.com/yang/openconfig/network-instances/deviations";
  prefix arista-network-instances-deviations;

  import openconfig-network-instance {
    prefix oc-netinst;
  }
  import openconfig-network-instance-types {
    prefix oc-ni-types;
  }
  import openconfig-extensions {
    prefix oc-ext;
  }
  import openconfig-vlan-types {
    prefix oc-vlan-types;
  }

  organization
    "Arista Networks, Inc.";
  contact
    "Arista Networks, Inc.
     Product Support";
  description
    "This module contains OpenConfig Network Instances deviations in Arista EOS.

     Copyright (c) 2017 Arista Networks, Inc. All rights reserved.";
  oc-ext:openconfig-version "1.1.4";

  revision 2024-01-28 {
    description
      "Add a deviation to fix missing leafref type";
    reference
      "1.2.0";
  }
  revision 2023-05-03 {
    description
      "Update deviation for network-instance to support L2VSI type";
    reference
      "1.2.0";
  }
  revision 2023-02-03 {
    description
      "Remove deviation for now supported flex algo metric type TE";
    reference
      "1.2.0";
  }
  revision 2022-12-20 {
    description
      "Remove deviation for recently removed enabled leaf";
    reference
      "1.1.5";
  }
  revision 2021-09-27 {
    description
      "pyang auto format";
    reference
      "1.1.4";
  }
  revision 2021-08-16 {
    description
      "Add a deviation for default-import-policy";
    reference
      "1.1.3";
  }
  revision 2021-07-16 {
    description
      "Add a deviation for metric-type";
    reference
      "1.1.2";
  }
  revision 2021-07-08 {
    description
      "MPLS must be in the default network instance.";
    reference
      "1.1.1";
  }
  revision 2021-04-01 {
    description
      "Add support for network-instance/config/enabled.";
    reference
      "1.1.0";
  }
  revision 2020-11-30 {
    description
      "Fix errors reported by pyang.";
    reference
      "1.0.2";
  }
  revision 2019-05-24 {
    description
      "Add prefixes to identity names in must statement.";
    reference
      "1.0.1";
  }
  revision 2017-11-10 {
    description
      "Initial deviation file.";
    reference
      "1.0.0";
  }

  deviation "/oc-netinst:network-instances/oc-netinst:network-instance/oc-netinst:inter-instance-policies/oc-netinst:apply-policy/oc-netinst:config/oc-netinst:default-import-policy" {
    description
      "default-import-policy is REJECT_ROUTE in EOS";
    deviate add {
      must "../default-import-policy = 'REJECT_ROUTE'" {
        error-message "default-import-policy can only be set to REJECT_ROUTE in EOS";
      }
    }
    deviate replace {
      default "REJECT_ROUTE";
    }
  }

  deviation "/oc-netinst:network-instances/oc-netinst:network-instance/oc-netinst:table-connections/oc-netinst:table-connection/oc-netinst:config/oc-netinst:default-import-policy" {
    description
      "default-import-policy is REJECT_ROUTE in EOS";
    deviate add {
      must "../default-import-policy = 'REJECT_ROUTE'" {
        error-message "default-import-policy can only be set to REJECT_ROUTE in EOS";
      }
    }
    deviate replace {
      default "REJECT_ROUTE";
    }
  }

  deviation "/oc-netinst:network-instances/oc-netinst:network-instance/oc-netinst:config" {
    description
      "only default and L3 instances are supported in EOS";
    deviate add {
      must "(type='oc-ni-types:DEFAULT_INSTANCE' and name='default') or (type='oc-ni-types:L3VRF' and name!='default') or (type='oc-ni-types:L2VSI' and name!='default')";
    }
  }

  deviation "/oc-netinst:network-instances/oc-netinst:network-instance/oc-netinst:vlans/oc-netinst:vlan/oc-netinst:members/oc-netinst:member/oc-netinst:state/oc-netinst:interface" {
    description
      "member interface can be an interface other than openconfig-interfaces:base-interface-ref, such as a subinterface, etc";
    deviate replace {
      type string;
    }
  }

  deviation "/oc-netinst:network-instances/oc-netinst:network-instance/oc-netinst:table-connections/oc-netinst:table-connection/oc-netinst:config/oc-netinst:import-policy" {
    description
      "import-policy can only have one leaf";
    deviate add {
      max-elements 1;
    }
  }

  deviation "/oc-netinst:network-instances/oc-netinst:network-instance/oc-netinst:mpls" {
    description
      "MPLS is only supported in the default network instance.";
    deviate add {
      must "../config/type = 'DEFAULT_INSTANCE'";
    }
  }

  deviation "/oc-netinst:network-instances/oc-netinst:network-instance/oc-netinst:fdb/oc-netinst:mac-table/oc-netinst:entries/oc-netinst:entry/oc-netinst:vlan" {
    description
      "mac-table entry vlan is type vlan-id";
    deviate replace {
      type oc-vlan-types:vlan-id;
    }
  }
}
