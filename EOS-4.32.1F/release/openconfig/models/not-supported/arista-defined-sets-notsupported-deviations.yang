module arista-defined-sets-notsupported-deviations {
  namespace "http://arista.com/yang/openconfig/defined-sets/notsupported-deviations";
  prefix arista-defined-sets-notsupported-deviations;

  import openconfig-defined-sets {
    prefix oc-sets;
  }

  organization
    "Arista Networks, Inc.";
  contact
    "Arista Networks, Inc.
     Product Support";
  description
    "This module contains OpenConfig defined-sets deviations in Arista EOS.
     Copyright (c) 2020 Arista Networks, Inc. All rights reserved.";

  revision 2024-05-24 {
    description
      "Auto-generated not-supported deviations for unsupported paths";
  }

  deviation "/oc-sets:defined-sets" {
    description
      "Not-supported deviation.";
    deviate not-supported;
  }
}
