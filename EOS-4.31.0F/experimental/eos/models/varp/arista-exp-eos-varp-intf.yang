module arista-exp-eos-varp-intf {
  yang-version 1;
  namespace "http://arista.com/yang/experimental/eos/varp/intf";
  prefix varp-exp-intf;

  import openconfig-interfaces {
    prefix oc-if;
  }
  import openconfig-if-ip {
    prefix oc-ip;
  }
  import iana-if-type {
    prefix ift;
  }

  organization
    "Arista Networks <http://arista.com/>";
  contact
    "Arista Networks, Inc.
     Product Support";
  description
    "This module contains OpenConfig VARP augments in Arista EOS.

     Copyright (c) 2018 Arista Networks, Inc. All rights reserved.";

  revision 2023-05-03 {
    description
      "Added secondary virtual IP addresses.";
  }
  revision 2020-01-06 {
    description
      "Removed unused imports.";
  }
  revision 2019-05-22 {
    description
      "Change namespace to be different from arista-exp-eos-varp-net-inst.";
  }
  revision 2018-10-01 {
    description
      "Initial revision";
    reference
      "0.1.0";
  }

  augment "/oc-if:interfaces/oc-if:interface" {
    when "oc-if:config/oc-if:type = 'ift:l3ipvlan'";
    description
      "VARP configuration for VLAN interfaces";
    container arista-varp {
      description
        "Top-level container for interface VARP configuration and state";
      container virtual-address {
        description
          "Virtual IP address for the VLAN interface";
        container config {
          description
            "Configuration data for virtual IP address";
          uses oc-ip:ipv4-address-config;
        }
        container state {
          config false;
          description
            "Operational state for virtual IP address";
          uses oc-ip:ipv4-address-config;
        }
      }
      container secondary-virtual-addresses {
        description
          "Secondary virtual IP addresses for the VLAN interface";
        list address {
          key "ip";
          description
           "List of secondary virtual ip addresses";
          leaf ip {
            type leafref {
              path "../config/ip";
            }
            description "References the configured IP address";
          }
          container config {
            description
              "Configuration data for secondary virtual IP address";
            uses oc-ip:ipv4-address-config;
          }
          container state {
            config false;
            description
               "Operational state data for secondary virtual IPv4 address";
            uses oc-ip:ipv4-address-config;
          }
        }
      }
    }
  }
}
