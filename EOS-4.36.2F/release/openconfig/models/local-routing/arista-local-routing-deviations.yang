module arista-local-routing-deviations {
  namespace "http://arista.com/yang/openconfig/local-routing/deviations";
  prefix arista-local-routing-deviations;

  import openconfig-network-instance {
    prefix oc-netinst;
  }
  import openconfig-extensions {
    prefix oc-ext;
  }

  organization
    "Arista Networks, Inc.";
  contact
    "Arista Networks, Inc.
     Product Support";
  description
    "This module contains OpenConfig local-routing deviations in Arista EOS.

     Copyright (c) 2017 Arista Networks, Inc. All rights reserved.";
  oc-ext:openconfig-version "1.0.5";

  revision 2024-07-16 {
    description
      "Remove recurse default value.";
    reference
      "1.0.6";
  }
  revision 2024-04-23 {
    description
      "Remove metric leaf range restriction deviation.";
    reference
      "1.0.5";
  }
  revision 2024-04-22 {
    description
      "Add preference leaf range restriction deviation.";
    reference
      "1.0.4";
  }
  revision 2024-02-01 {
    description
      "Remove recurse not-supported deviation.";
    reference
      "1.0.3";
  }
  revision 2023-09-06 {
    description
      "Remove interface-ref subinterface not-supported deviation.";
    reference
      "1.0.2";
  }
  revision 2020-11-30 {
    description
      "Fix errors reported by pyang.";
    reference
      "1.0.1";
  }
  revision 2017-11-22 {
    description
      "Initial deviations file.";
    reference
      "1.0.0";
  }

  deviation "/oc-netinst:network-instances/oc-netinst:network-instance/oc-netinst:protocols/oc-netinst:protocol/oc-netinst:static-routes/oc-netinst:static/oc-netinst:next-hops/oc-netinst:next-hop/oc-netinst:config/oc-netinst:recurse" {
    description
      "unset recurse corresponds to the default resolution rib profile in EOS";
    deviate delete {
      default false;
    }
  }

  deviation "/oc-netinst:network-instances/oc-netinst:network-instance/oc-netinst:protocols/oc-netinst:protocol/oc-netinst:static-routes/oc-netinst:static/oc-netinst:next-hops/oc-netinst:next-hop/oc-netinst:config/oc-netinst:preference" {
    description
      "preference EOS range restriction. preference for static routes corresponds to their administrative distance in EOS";
    deviate replace {
      type uint32 {
        range "1..255";
      }
    }
  }
  
  deviation "/oc-netinst:network-instances/oc-netinst:network-instance/oc-netinst:protocols/oc-netinst:protocol/oc-netinst:static-routes/oc-netinst:static/oc-netinst:config/oc-netinst:set-tag" {
    description
      "set-tag EOS restriction. set-tag for static routes may only be set to a decimal value";
    deviate replace {
      type uint32;
    }
  }

  deviation "/oc-netinst:network-instances/oc-netinst:network-instance/oc-netinst:protocols/oc-netinst:protocol/oc-netinst:config/oc-netinst:default-metric" {
    description
      "configuring default-metric is not supported by EOS";
    deviate not-supported;
  }
}
