module arista-aft-deviations {
  namespace "http://arista.com/yang/openconfig/aft/deviations";
  prefix arista-aft-deviations;

  import openconfig-network-instance {
    prefix oc-netinst;
  }
  import openconfig-extensions {
    prefix oc-ext;
  }

  organization
    "Arista Networks, Inc.";
  contact
    "Arista Networks, Inc.
     Product Support";
  description
    "This module contains OpenConfig AFT deviations in Arista EOS.

     Copyright (c) 2025 Arista Networks, Inc. All rights reserved.";
  oc-ext:openconfig-version "1.0.0";

  revision 2025-12-01 {
    description
      "Deviations to add back atomic-exempt, recently removed from the standard model.";
    reference
      "1.0.0";
  }

  deviation
    "/oc-netinst:network-instances/oc-netinst:network-instance/oc-netinst:afts/"
  + "oc-netinst:next-hops/oc-netinst:next-hop/oc-netinst:state/oc-netinst:counters" {
    deviate add {
      oc-ext:telemetry-atomic-exempt;
      }
  }

  deviation
    "/oc-netinst:network-instances/oc-netinst:network-instance/oc-netinst:afts/"
  + "oc-netinst:ipv4-unicast/oc-netinst:ipv4-entry/oc-netinst:state/oc-netinst:counters" {
    deviate add {
      oc-ext:telemetry-atomic-exempt;
      }
  }

  deviation
    "/oc-netinst:network-instances/oc-netinst:network-instance/oc-netinst:afts/"
  + "oc-netinst:mpls/oc-netinst:label-entry/oc-netinst:state/oc-netinst:counters" {
    deviate add {
      oc-ext:telemetry-atomic-exempt;
      }
  }
}
