module arista-acl-notsupported-deviations {
  namespace "http://arista.com/yang/openconfig/acl/notsupported-deviations";
  prefix arista-acl-notsupported-deviations;

  import openconfig-acl {
    prefix oc-acl;
  }

  organization
    "Arista Networks, Inc.";
  contact
    "Arista Networks, Inc.
     Product Support";
  description
    "This module contains OpenConfig acl deviations in Arista EOS.
     Copyright (c) 2020 Arista Networks, Inc. All rights reserved.";

  revision 2026-08-06 {
    description
      "Auto-generated not-supported deviations for unsupported paths";
  }

  deviation "/oc-acl:acl/oc-acl:acl-sets/oc-acl:acl-set/oc-acl:acl-entries/oc-acl:acl-entry/oc-acl:mpls" {
    description
      "Not-supported deviation.";
    deviate not-supported;
  }

  deviation "/oc-acl:acl/oc-acl:acl-sets/oc-acl:acl-set/oc-acl:acl-entries/oc-acl:acl-entry/oc-acl:ipv4/oc-acl:config/oc-acl:fragment-offsets" {
    description
      "Not-supported deviation.";
    deviate not-supported;
  }

  deviation "/oc-acl:acl/oc-acl:acl-sets/oc-acl:acl-set/oc-acl:acl-entries/oc-acl:acl-entry/oc-acl:ipv4/oc-acl:state/oc-acl:fragment-offsets" {
    description
      "Not-supported deviation.";
    deviate not-supported;
  }
}
