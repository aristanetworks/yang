module arista-defined-sets-notsupported-deviations {
  namespace "http://arista.com/yang/openconfig/defined-sets/notsupported-deviations";
  prefix arista-defined-sets-notsupported-deviations;

  import openconfig-defined-sets {
    prefix oc-sets;
  }

  organization
    "Arista Networks, Inc.";
  contact
    "Arista Networks, Inc.
     Product Support";
  description
    "This module contains OpenConfig defined-sets deviations in Arista EOS.
     Copyright (c) 2020 Arista Networks, Inc. All rights reserved.";

  revision 2026-08-06 {
    description
      "Auto-generated not-supported deviations for unsupported paths";
  }

  deviation "/oc-sets:defined-sets/oc-sets:ipv4-prefix-sets/oc-sets:ipv4-prefix-set/oc-sets:config/oc-sets:description" {
    description
      "Not-supported deviation.";
    deviate not-supported;
  }

  deviation "/oc-sets:defined-sets/oc-sets:ipv4-prefix-sets/oc-sets:ipv4-prefix-set/oc-sets:state/oc-sets:description" {
    description
      "Not-supported deviation.";
    deviate not-supported;
  }

  deviation "/oc-sets:defined-sets/oc-sets:ipv6-prefix-sets/oc-sets:ipv6-prefix-set/oc-sets:config/oc-sets:description" {
    description
      "Not-supported deviation.";
    deviate not-supported;
  }

  deviation "/oc-sets:defined-sets/oc-sets:ipv6-prefix-sets/oc-sets:ipv6-prefix-set/oc-sets:state/oc-sets:description" {
    description
      "Not-supported deviation.";
    deviate not-supported;
  }

  deviation "/oc-sets:defined-sets/oc-sets:port-sets/oc-sets:port-set/oc-sets:config/oc-sets:description" {
    description
      "Not-supported deviation.";
    deviate not-supported;
  }

  deviation "/oc-sets:defined-sets/oc-sets:port-sets/oc-sets:port-set/oc-sets:state/oc-sets:description" {
    description
      "Not-supported deviation.";
    deviate not-supported;
  }
}
