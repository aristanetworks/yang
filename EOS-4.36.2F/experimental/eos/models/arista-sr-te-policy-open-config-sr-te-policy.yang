module arista-sr-te-policy-open-config-sr-te-policy {
  yang-version 1;
  namespace "http://arista.com/yang/arista-sr-te-policy-open-config-sr-te-policy";
  prefix "arista-sr-te-policy-open-config-sr-te-policy";
  
  import openconfig-extensions { prefix "oc-ext"; }
  import arista-sr-te-policy-lib-sr-te-policy-basic-types { prefix "arista-sr-te-policy-lib-sr-te-policy-basic-types"; }
  import openconfig-inet-types { prefix "openconfig-inet-types"; }
  import openconfig-mpls-types { prefix "openconfig-mpls-types"; }
  
  organization
    "Arista Networks <http://arista.com/>";
  contact
    "Arista Networks <http://arista.com/>";
  
  description
    "This is the model for policy forwarding model SrTe extensions
    THIS YANG MODULE WAS GENERATED. DO NOT EDIT THIS FILE.";
  
  oc-ext:openconfig-version "1.0.0";
  
  revision "2026-01-09" {
    description
      "Version 1.0.0, generated on 2026-01-09";
    reference "1.0.0";
  }
  // covered-by: openconfig-pf-srte.yang,arista-srte-augments.yang
  
  grouping sr-te-policy-open-config-pf-policy-seg-key {
    leaf index {
      type uint64;
      description
        "index";
    }
    description
      "sr-te-policy-open-config-pf-policy-seg-key";
  }
  grouping sr-te-policy-open-config-pf-policy-srte-config {
    leaf explicit-null-label {
      type arista-sr-te-policy-lib-sr-te-policy-basic-types:sr-te-policy-enlp-enum;
      description
        "Add explicit null label into PF SRTE configuration.";
    }
    leaf mpls-bsid {
      type openconfig-mpls-types:mpls-label;
      description
        "mpls-bsid";
    }
    leaf srte-color {
      type uint32;
      description
        "srte-color";
    }
    leaf srte-endpoint {
      type openconfig-inet-types:ip-address;
      description
        "srte-endpoint";
    }
    leaf srte-preference {
      type uint32;
      description
        "srte-preference";
    }
    description
      "sr-te-policy-open-config-pf-policy-srte-config";
  }
  grouping sr-te-policy-open-config-pf-policy-srte-key {
    description
      "sr-te-policy-open-config-pf-policy-srte-key";
  }
  grouping sr-te-policy-open-config-pf-policy-srte {
    uses sr-te-policy-open-config-pf-policy-srte-key;
    container config {
      uses sr-te-policy-open-config-pf-policy-srte-config;
      description
        "config";
    }
    container state {
      uses sr-te-policy-open-config-pf-policy-srte-config;
      config false;
      description
        "state";
    }
    description
      "sr-te-policy-open-config-pf-policy-srte";
  }
  grouping sr-te-policy-open-config-pf-policy-seg-list-config {
    leaf index {
      type uint64;
      description
        "index";
    }
    leaf weight {
      type uint32;
      description
        "weight";
    }
    description
      "sr-te-policy-open-config-pf-policy-seg-list-config";
  }
  grouping sr-te-policy-open-config-pf-policy-sid-config {
    leaf index {
      type uint64;
      description
        "index";
    }
    leaf value {
      type openconfig-mpls-types:mpls-label;
      description
        "value";
    }
    description
      "sr-te-policy-open-config-pf-policy-sid-config";
  }
  grouping sr-te-policy-open-config-pf-policy-sid {
    leaf index {
      type uint64;
      description
        "index";
    }
    container config {
      uses sr-te-policy-open-config-pf-policy-sid-config;
      description
        "config";
    }
    container state {
      uses sr-te-policy-open-config-pf-policy-sid-config;
      config false;
      description
        "state";
    }
    description
      "sr-te-policy-open-config-pf-policy-sid";
  }
  grouping sr-te-policy-open-config-pf-policy-sids {
    list sid {
      key "index";
      uses sr-te-policy-open-config-pf-policy-sid;
      description
        "sid";
    }
    description
      "sr-te-policy-open-config-pf-policy-sids";
  }
  grouping sr-te-policy-open-config-pf-policy-seg-list {
    uses sr-te-policy-open-config-pf-policy-seg-key;
    container config {
      uses sr-te-policy-open-config-pf-policy-seg-list-config;
      description
        "config";
    }
    container state {
      uses sr-te-policy-open-config-pf-policy-seg-list-config;
      config false;
      description
        "state";
    }
    container sids {
      uses sr-te-policy-open-config-pf-policy-sids;
      description
        "sids";
    }
    description
      "sr-te-policy-open-config-pf-policy-seg-list";
  }
  container network-instances {
    list network-instance {
      key "name";
      oc-ext:telemetry-atomic;
      leaf name {
        type string;
        description
          "name leaf used as key for network-instance list";
      }
      container policy-forwarding {
        container policies {
          list policy {
            key "policy-id";
            oc-ext:telemetry-atomic;
            leaf policy-id {
              type string;
              description
                "policy-id leaf used as key for policy list";
            }
            container rules {
              list rule {
                key "sequence-id";
                oc-ext:telemetry-atomic;
                leaf sequence-id {
                  type uint32;
                  description
                    "sequence-id leaf used as key for rule list";
                }
                container srte {
                  uses sr-te-policy-open-config-pf-policy-srte;
                  description
                    "srte container";
                }
                container action {
                  container segment-lists {
                    list segment-list {
                      key "index";
                      oc-ext:telemetry-atomic;
                      uses sr-te-policy-open-config-pf-policy-seg-list;
                      description
                        "segment-list list";
                    }
                    oc-ext:telemetry-atomic;
                    description
                      "segment-lists container";
                  }
                  oc-ext:telemetry-atomic;
                  description
                    "action container";
                }
                description
                  "rule list";
              }
              oc-ext:telemetry-atomic;
              description
                "rules container";
            }
            description
              "policy list";
          }
          oc-ext:telemetry-atomic;
          description
            "policies container";
        }
        oc-ext:telemetry-atomic;
        description
          "policy-forwarding container";
      }
      description
        "network-instance list";
    }
    oc-ext:telemetry-atomic;
    description
      "network-instances container";
  }
} // main-yang
