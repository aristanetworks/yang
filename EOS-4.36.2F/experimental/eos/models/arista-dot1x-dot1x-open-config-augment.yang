module arista-dot1x-dot1x-open-config-augment {
  yang-version 1;
  namespace "http://arista.com/yang/arista-dot1x-dot1x-open-config-augment";
  prefix "arista-dot1x-dot1x-open-config-augment";
  
  import openconfig-extensions { prefix "oc-ext"; }
  import arista-dot1x-dot1x { prefix "arista-dot1x-dot1x"; }
  import arista-eos-types { prefix "arista-eos-types"; }
  import openconfig-if-8021x { prefix "openconfig-if-8021x"; }
  import openconfig-if-ethernet { prefix "openconfig-if-ethernet"; }
  import openconfig-inet-types { prefix "openconfig-inet-types"; }
  import openconfig-interfaces { prefix "openconfig-interfaces"; }
  import openconfig-vlan-types { prefix "openconfig-vlan-types"; }
  import openconfig-yang-types { prefix "openconfig-yang-types"; }
  
  organization
    "Arista Networks <http://arista.com/>";
  contact
    "Arista Networks <http://arista.com/>";
  
  description
    "Arista augmentations model for Dot1x
    THIS YANG MODULE WAS GENERATED. DO NOT EDIT THIS FILE.";
  
  oc-ext:openconfig-version "1.0.0";
  
  revision "2025-08-26" {
    description
      "Version 1.0.0, generated on 2025-08-26";
    reference "1.0.0";
  }
  typedef dot1x-open-config-service-type-enum {
    type enumeration {
      enum LOGIN {
        value 1;
        description
          "LOGIN";
      }
      enum FRAMED {
        value 2;
        description
          "FRAMED";
      }
      enum CALLBACK_LOGIN {
        value 3;
        description
          "CALLBACK_LOGIN";
      }
      enum CALLBACK_FRAMED {
        value 4;
        description
          "CALLBACK_FRAMED";
      }
      enum OUTBOUND {
        value 5;
        description
          "OUTBOUND";
      }
      enum ADMINISTRATIVE {
        value 6;
        description
          "ADMINISTRATIVE";
      }
      enum NAS_PROMPT {
        value 7;
        description
          "NAS_PROMPT";
      }
      enum AUTHENTICATE_ONLY {
        value 8;
        description
          "AUTHENTICATE_ONLY";
      }
      enum CALLBACK_NAS_PROMPT {
        value 9;
        description
          "CALLBACK_NAS_PROMPT";
      }
      enum CALL_CHECK {
        value 10;
        description
          "CALL_CHECK";
      }
      enum CALLBACK_ADMINISTRATIVE {
        value 11;
        description
          "CALLBACK_ADMINISTRATIVE";
      }
    }
    description
      "Supplicant Service-Type. Reference: RFC2865 Section-5.6 Service-Type";
  }
  typedef dot1x-open-config-supp-auth-nzstatus {
    type enumeration {
      enum SOFTWARE_CACHED {
        value 0;
        description
          "The session is no longer authenticated, but session is retained as cached-results.";
      }
      enum DISCONNECTED_CACHED {
        value 1;
        description
          "The session is successfully authenticated and retained as cached-results after link down.";
      }
      enum SUCCESS_CACHED {
        value 2;
        description
          "The session is succesfully authenticated using cached-results.";
      }
      enum IDLE {
        value 3;
        description
          "The session is in an idle state (not authenticated), with no ongoing authentication, authorization, or accounting.";
      }
      enum AUTH_WAIT_FOR_SUPPLICANT {
        value 4;
        description
          "The session is waiting for response from Supplicant.";
      }
      enum AUTH_WAIT_FOR_AUTH_SERVER {
        value 5;
        description
          "The session is waiting for response from AAA server.";
      }
      enum RE_AUTH_WAIT_FOR_SUPPLICANT {
        value 6;
        description
          "The session is reauthenticating and waiting for response from Supplicant.";
      }
      enum RE_AUTH_WAIT_FOR_AUTH_SERVER {
        value 7;
        description
          "The session is reauthenticating and waiting for response from AAA server.";
      }
      enum WEB_AUTH_START {
        value 8;
        description
          "The session has started web authentication and is awaiting its completion.";
      }
      enum SUCCESSFUL_AUTH {
        value 9;
        description
          "The session has succesfully authenticated and authorized.";
      }
      enum SUPPLICANT_TIMEOUT {
        value 10;
        description
          "An authentication has been attempted for this session, however the supplicant has not responded.";
      }
      enum AUTH_SERVER_TIMEOUT {
        value 11;
        description
          "An authentication has been attempted for this session, however the AAA server has not responded.";
      }
      enum FAILED_AUTH {
        value 12;
        description
          "The session's authentication and/or authorization attempt has failed.";
      }
      enum FAILED_UNTAGGED_DYN_VLAN {
        value 13;
        description
          "The session's authorization attempt has failed because VLAN identifier for the supplicant cannot be applied due to port state.";
      }
      enum FAILED_TAGGED_DYN_VLAN {
        value 14;
        description
          "The session's authorization attempt has failed because VLAN identifier received from AAA server does not match the VLAN identifier of the packet received from the Supplicant.";
      }
      enum FAILED_INTERNAL_VLAN {
        value 15;
        description
          "The session's authorization attempt has failed due to conflict between internal VLAN and dynamic VLAN associated with the Supplicant.";
      }
      enum FAILED_ACL_ATTACHMENT {
        value 16;
        description
          "The session's authorization attempt has failed due to anissue with ACL config received by AAA server or ACL config on the switch.";
      }
      enum FAILED_DYNAMIC_ACL_CREATION {
        value 17;
        description
          "The session's authorization attempt has failed because the NAS-Filter-Rule received from AAA could not be applied due to dynamic ACL creation error.";
      }
      enum FAILED_STATIC_AND_DYNAMIC_ACL {
        value 18;
        description
          "The session's authorization attempt has failed because both an ACL and a NAS-Filter-Rule were received from AAA, which is not supported.";
      }
      enum FAILED_WEB_AUTH {
        value 19;
        description
          "The session's authorization attempt has failed due to failed web authentication.";
      }
      enum FAILED_MVRP {
        value 20;
        description
          "The session's authorization attempt has failed due to conflicting MVRP config sent by the AAA server or due to an incorrect configuration on the port.";
      }
      enum FAILED_VLAN_NAME {
        value 21;
        description
          "The session's authorization attempt has failed because the VLAN name received from AAA was invalid.";
      }
      enum FAILED_INVALID_ATTRIBUTE {
        value 22;
        description
          "The session's authorization attempt has failed because it attempted to utilize a feature that is not valid.";
      }
      enum FAILED_UNSUPPORTED_ATTRIBUTE {
        value 23;
        description
          "The session's authorization attempt has failed because it attempted to utilize a feature that is not supported.";
      }
      enum PENDING_DELETION {
        value 24;
        description
          "The session has been marked for deletion and is waiting to be cleared.";
      }
    }
    description
      "";
  }
  typedef dot1x-open-config-termination-action-enum {
    type enumeration {
      enum DEFAULT {
        value 0;
        description
          "DEFAULT";
      }
      enum RADIUS_REQUEST {
        value 1;
        description
          "RADIUS_REQUEST";
      }
    }
    description
      "dot1x-open-config-termination-action-enum";
  }
  typedef dot1x-open-config-service-type {
    type union {
      type uint32;
      type dot1x-open-config-service-type-enum;
    }
    description
      "dot1x-open-config-service-type";
  }
  typedef dot1x-open-config-termination-action {
    type union {
      type dot1x-open-config-termination-action-enum;
      type uint32;
    }
    description
      "Supplicant Termination-Action. Reference: RFC2865 Section-5.29 Termination-Action";
  }
  grouping dot1x-open-config-supp-key {
    description
      "dot1x-open-config-supp-key";
  }
  grouping dot1x-open-config-aaa-provided-attrs {
    leaf class {
      type binary;
      description
        "Supplicant Class. Reference: RFC2865 Section-5.25 Class";
    }
    leaf arista-device-type {
      type arista-dot1x-dot1x:dot1x-device-type;
      description
        "Device Type classification received from AAA as Vendor-specific attribute";
    }
    leaf filter-id {
      type string;
      description
        "Supplicant Filter-Id. Reference: RFC2865 Section-5.11 Filter-Id";
    }
    leaf idle-timeout {
      type arista-eos-types:seconds;
      units seconds;
      description
        "Supplicant Idle-Timeout in seconds. Reference: RFC2865 Section-5.28 Idle-Timeout";
    }
    leaf arista-interface-profile {
      type string;
      description
        "Supplicant Arista-Interface-Profile Vendor-specific attribute";
    }
    leaf arista-mvrp {
      type arista-dot1x-dot1x:dot1x-mvrp-state;
      description
        "Supplicant Arista-Mvrp Vendor-specific attribute";
    }
    leaf-list nas-filter-rule {
      type string;
      oc-ext:telemetry-atomic;
      description
        "The list of supplicant NAS-Filter-Rule. Reference: RFC4849 Section-2 NAS-Filter-Rule Attribute";
    }
    leaf arista-periodic-identity {
      type string;
      description
        "Supplicant Arista-PeriodicIdentity Vendor-specific attributes";
    }
    leaf reauthenticate-behavior {
      type arista-dot1x-dot1x:dot1x-reauth-behavior;
      description
        "Re-authentication behavior received from AAA";
    }
    leaf session-timeout {
      type uint32;
      units seconds;
      description
        "Session-timeout received from AAA";
    }
    leaf arista-tenant-id {
      type uint16;
      description
        "Supplicant Arista-Tenant-Id Vendor-specific attribute";
    }
    leaf termination-action {
      type dot1x-open-config-termination-action;
      description
        "Supplicant Termination-Action. Reference: RFC2865 Section-5.29 Termination-Action";
    }
    leaf tunnel-private-group-id {
      type string;
      description
        "Supplicant Tunnel-Private-GroupId. Reference: RFC2868 Section-3.6 Tunnel-Private-Group-ID";
    }
    leaf arista-web-auth {
      type string;
      description
        "Supplicant Arista-WebAuth Vendor-specific attribute";
    }
    description
      "dot1x-open-config-aaa-provided-attrs";
  }
  grouping dot1x-open-config-dot1x-ocsupplicant {
    uses dot1x-open-config-supp-key;
    leaf auth-status {
      type dot1x-open-config-supp-auth-nzstatus;
      description
        "The state of the session for a supplicant";
    }
    leaf auth-method {
      type arista-dot1x-dot1x:dot1x-auth-method;
      description
        "Authentication method used by the supplicant";
    }
    leaf identity {
      type string;
      description
        "Identity used by the supplicant during authentication";
    }
    leaf vlan-id {
      type openconfig-vlan-types:vlan-id;
      description
        "VLAN identifier used by supplicant";
    }
    leaf framed-ip-address {
      type openconfig-inet-types:ipv4-address;
      description
        "Supplicant Framed-IP-Address";
    }
    leaf framed-ip-address-source {
      type arista-dot1x-dot1x:dot1x-framed-ip-source;
      description
        "Supplicant Framed-IP-Address source";
    }
    leaf framed-ipv6-address {
      type openconfig-inet-types:ipv6-address;
      description
        "Supplicant Framed-IPv6-Address";
    }
    leaf framed-ipv6-address-source {
      type arista-dot1x-dot1x:dot1x-framed-ip-source;
      description
        "Supplicant Framed-IPv6-Address source";
    }
    leaf captive-portal {
      type string;
      description
        "Supplicant Captive portal";
    }
    leaf captive-portal-source {
      type string;
      description
        "Supplicant Captive portal source";
    }
    leaf reauthenticate-behavior {
      type arista-dot1x-dot1x:dot1x-reauth-behavior;
      description
        "Supplicant re-authentication behavior";
    }
    leaf next-reauthenticate-timestamp {
      type arista-eos-types:seconds;
      description
        "UTC timestamp for upcoming re-authentication of supplicant";
    }
    leaf reauthenticate-interval {
      type uint32;
      units seconds;
      description
        "Supplicant re-authentication interval in seconds";
    }
    leaf service-type {
      type dot1x-open-config-service-type;
      description
        "Supplicant Service-Type. Reference: RFC2865 Section-5.6 Service-Type";
    }
    description
      "dot1x-open-config-dot1x-ocsupplicant";
  }
  grouping dot1x-open-config-dot1x-ocintf-counter {
    leaf eapol-success {
      type uint32;
      description
        "Count of EAPoL supplicants in success state";
    }
    leaf mba-success {
      type uint32;
      description
        "Count of MAC-based Authentication supplicants in success state";
    }
    leaf eapol-failed {
      type uint32;
      description
        "Count of EAPoL supplicants in failed state";
    }
    leaf mba-failed {
      type uint32;
      description
        "Count of MAC-based Authentication supplicants in failed state";
    }
    leaf eapol-cached {
      type uint32;
      description
        "Count of EAPoL supplicants in cached state";
    }
    leaf mba-cached {
      type uint32;
      description
        "Count of MAC-based Authentication supplicants in cached state";
    }
    leaf eapol-fallback-total {
      type uint32;
      description
        "Count of EAPoL supplicants in all fallback states";
    }
    leaf mba-fallback-total {
      type uint32;
      description
        "Count of MAC-based Authentication supplicants in all fallback states";
    }
    leaf aaa-unresp {
      type uint32;
      description
        "Count of supplicants in AAA unresponsive VLAN";
    }
    leaf aaa-unresp-phone {
      type uint32;
      description
        "Count of supplicants in AAA unresponsive phone VLAN";
    }
    leaf auth-fail {
      type uint32;
      description
        "Count of supplicants in auth-fail VLAN";
    }
    leaf guest {
      type uint32;
      description
        "Count of supplicants in guest VLAN";
    }
    leaf eapol-to-mba-fallback {
      type uint32;
      description
        "Count of supplicants in EAPoL to MAC-based Authentication fallback";
    }
    leaf web-auth {
      type uint32;
      description
        "Count of web-auth supplicants";
    }
    leaf total-supplicant {
      type uint32;
      description
        "Count of all supplicants";
    }
    description
      "dot1x-open-config-dot1x-ocintf-counter";
  }
  grouping dot1x-open-config-dot1x-ocintf-status {
    leaf authorization-state {
      type arista-dot1x-dot1x:dot1x-port-auth-state;
      description
        "Authorization state of the interface";
    }
    leaf port-control {
      type arista-dot1x-dot1x:dot1x-port-ctrl-setting;
      description
        "802.1X port control state of the interface";
    }
    leaf force-phone-authorization {
      type boolean;
      description
        "When it is True, forced authorization is enabled for phone devices";
    }
    leaf session-replace {
      type boolean;
      description
        "When it is True, session replace is allowed in single-host mode";
    }
    leaf quiet-interval {
      type uint16;
      units seconds;
      description
        "Waiting period in seconds after a failed authentication";
    }
    leaf reauthenticate-server-fail-ignore {
      type boolean;
      description
        "Retain current port authorization status on AAA server timeout or supplicant timeouts";
    }
    leaf unauthorized-access-vlan-egress {
      type boolean;
      description
        "Give unauthorized access port egress membership of access VLAN";
    }
    leaf unauthorized-native-vlan-egress {
      type boolean;
      description
        "Give unauthorized trunk port egress membership of native VLAN";
    }
    leaf disable-eapol-auth {
      type boolean;
      description
        "When this leaf is set to true, EAPoL authentication is disabled";
    }
    leaf mac-based-auth {
      type boolean;
      description
        "When it is True, MAC-based authentication is enabled on the interface";
    }
    leaf mac-based-auth-fallback-timeout {
      type uint16;
      units seconds;
      description
        "Timeout for starting MAC-based authentication for non-EAPoL clients in seconds if MAC-based Authentication fallback is enabled";
    }
    leaf mac-based-auth-fallback {
      type boolean;
      description
        "When it is True, MAC-based Authentication fallback is enabled and applies if EAPoL authentication fails";
    }
    leaf mac-based-auth-host-mode {
      type boolean;
      description
        "When it is True, host mode also applies to MAC-based authentication";
    }
    leaf idle-timeout {
      type arista-eos-types:seconds;
      units seconds;
      description
        "Idle-Timeout for supplicants in seconds";
    }
    leaf always-mac-based-auth {
      type boolean;
      description
        "Attempt both MAC-based authentication (MBA) and EAPoL authentication simultaneously, retaining a successful MAC-based authentication session if EAPoL authentication fails, and overriding the MAC-based Authentication session only upon EAPoL authentication success";
    }
    leaf dynamic-authorization {
      type boolean;
      description
        "When it is True, 802.1x dynamic authorization is enabled on the interface. Reference RFC5176";
    }
    leaf bypass-lldp {
      type boolean;
      description
        "Allow LLDP packets regardless of port authorization state";
    }
    leaf bypass-bpdu {
      type boolean;
      description
        "Allow BPDU packets regardless of port authorization state";
    }
    leaf bypass-lacp {
      type boolean;
      description
        "Allow LACP packets regardless of port authorization state";
    }
    leaf bypass-loop-protection {
      type boolean;
      description
        "Allow loop protection packets regardless of port authorization state";
    }
    leaf eapol-session-move {
      type boolean;
      description
        "When it is True, session move is allowed for EAPoL supplicants";
    }
    leaf frequent-session-replace-action {
      type arista-dot1x-dot1x:dot1x-session-replace-detection;
      description
        "Action to take when more than 5 session replacements detected within 30 seconds";
    }
    leaf port-recovery-timestamp {
      type arista-eos-types:seconds;
      description
        "UTC timestamp till when port will remain disabled as requested by AAA";
    }
    description
      "dot1x-open-config-dot1x-ocintf-status";
  }
  augment "/openconfig-interfaces:interfaces/openconfig-interfaces:interface/openconfig-if-ethernet:ethernet/openconfig-if-8021x:authenticated-sessions/openconfig-if-8021x:authenticated-session" {
    container aaa-provided-attributes {
      container state {
        uses dot1x-open-config-aaa-provided-attrs;
        config false;
        description
          "Attributes returned from the AAA server for the session";
      }
      description
        "aaa-provided-attributes container";
    }
    description
      "";
  }
  augment "/openconfig-interfaces:interfaces/openconfig-interfaces:interface/openconfig-if-ethernet:ethernet/openconfig-if-8021x:authenticated-sessions/openconfig-if-8021x:authenticated-session/openconfig-if-8021x:state" {
    leaf auth-status {
      type dot1x-open-config-supp-auth-nzstatus;
      description
        "The state of the session for a supplicant";
    }
    leaf auth-method {
      type arista-dot1x-dot1x:dot1x-auth-method;
      description
        "Authentication method used by the supplicant";
    }
    leaf identity {
      type string;
      description
        "Identity used by the supplicant during authentication";
    }
    leaf vlan-id {
      type openconfig-vlan-types:vlan-id;
      description
        "VLAN identifier used by supplicant";
    }
    leaf framed-ip-address {
      type openconfig-inet-types:ipv4-address;
      description
        "Supplicant Framed-IP-Address";
    }
    leaf framed-ip-address-source {
      type arista-dot1x-dot1x:dot1x-framed-ip-source;
      description
        "Supplicant Framed-IP-Address source";
    }
    leaf framed-ipv6-address {
      type openconfig-inet-types:ipv6-address;
      description
        "Supplicant Framed-IPv6-Address";
    }
    leaf framed-ipv6-address-source {
      type arista-dot1x-dot1x:dot1x-framed-ip-source;
      description
        "Supplicant Framed-IPv6-Address source";
    }
    leaf captive-portal {
      type string;
      description
        "Supplicant Captive portal";
    }
    leaf captive-portal-source {
      type string;
      description
        "Supplicant Captive portal source";
    }
    leaf reauthenticate-behavior {
      type arista-dot1x-dot1x:dot1x-reauth-behavior;
      description
        "Supplicant re-authentication behavior";
    }
    leaf next-reauthenticate-timestamp {
      type arista-eos-types:seconds;
      description
        "UTC timestamp for upcoming re-authentication of supplicant";
    }
    leaf reauthenticate-interval {
      type uint32;
      units seconds;
      description
        "Supplicant re-authentication interval in seconds";
    }
    leaf service-type {
      type dot1x-open-config-service-type;
      description
        "Supplicant Service-Type. Reference: RFC2865 Section-5.6 Service-Type";
    }
    description
      "";
  }
  augment "/openconfig-interfaces:interfaces/openconfig-interfaces:interface/openconfig-if-ethernet:ethernet/openconfig-if-8021x:dot1x/openconfig-if-8021x:state" {
    leaf authorization-state {
      type arista-dot1x-dot1x:dot1x-port-auth-state;
      description
        "Authorization state of the interface";
    }
    leaf port-control {
      type arista-dot1x-dot1x:dot1x-port-ctrl-setting;
      description
        "802.1X port control state of the interface";
    }
    leaf force-phone-authorization {
      type boolean;
      description
        "When it is True, forced authorization is enabled for phone devices";
    }
    leaf session-replace {
      type boolean;
      description
        "When it is True, session replace is allowed in single-host mode";
    }
    leaf quiet-interval {
      type uint16;
      units seconds;
      description
        "Waiting period in seconds after a failed authentication";
    }
    leaf reauthenticate-server-fail-ignore {
      type boolean;
      description
        "Retain current port authorization status on AAA server timeout or supplicant timeouts";
    }
    leaf unauthorized-access-vlan-egress {
      type boolean;
      description
        "Give unauthorized access port egress membership of access VLAN";
    }
    leaf unauthorized-native-vlan-egress {
      type boolean;
      description
        "Give unauthorized trunk port egress membership of native VLAN";
    }
    leaf disable-eapol-auth {
      type boolean;
      description
        "When this leaf is set to true, EAPoL authentication is disabled";
    }
    leaf mac-based-auth {
      type boolean;
      description
        "When it is True, MAC-based authentication is enabled on the interface";
    }
    leaf mac-based-auth-fallback-timeout {
      type uint16;
      units seconds;
      description
        "Timeout for starting MAC-based authentication for non-EAPoL clients in seconds if MAC-based Authentication fallback is enabled";
    }
    leaf mac-based-auth-fallback {
      type boolean;
      description
        "When it is True, MAC-based Authentication fallback is enabled and applies if EAPoL authentication fails";
    }
    leaf mac-based-auth-host-mode {
      type boolean;
      description
        "When it is True, host mode also applies to MAC-based authentication";
    }
    leaf idle-timeout {
      type arista-eos-types:seconds;
      units seconds;
      description
        "Idle-Timeout for supplicants in seconds";
    }
    leaf always-mac-based-auth {
      type boolean;
      description
        "Attempt both MAC-based authentication (MBA) and EAPoL authentication simultaneously, retaining a successful MAC-based authentication session if EAPoL authentication fails, and overriding the MAC-based Authentication session only upon EAPoL authentication success";
    }
    leaf dynamic-authorization {
      type boolean;
      description
        "When it is True, 802.1x dynamic authorization is enabled on the interface. Reference RFC5176";
    }
    leaf bypass-lldp {
      type boolean;
      description
        "Allow LLDP packets regardless of port authorization state";
    }
    leaf bypass-bpdu {
      type boolean;
      description
        "Allow BPDU packets regardless of port authorization state";
    }
    leaf bypass-lacp {
      type boolean;
      description
        "Allow LACP packets regardless of port authorization state";
    }
    leaf bypass-loop-protection {
      type boolean;
      description
        "Allow loop protection packets regardless of port authorization state";
    }
    leaf eapol-session-move {
      type boolean;
      description
        "When it is True, session move is allowed for EAPoL supplicants";
    }
    leaf frequent-session-replace-action {
      type arista-dot1x-dot1x:dot1x-session-replace-detection;
      description
        "Action to take when more than 5 session replacements detected within 30 seconds";
    }
    leaf port-recovery-timestamp {
      type arista-eos-types:seconds;
      description
        "UTC timestamp till when port will remain disabled as requested by AAA";
    }
    container counters {
      uses dot1x-open-config-dot1x-ocintf-counter;
      description
        "A collection of interface specific statistics";
    }
    description
      "";
  }
} // augment-yang
