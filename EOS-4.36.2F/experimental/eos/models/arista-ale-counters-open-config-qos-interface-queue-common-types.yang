module arista-ale-counters-open-config-qos-interface-queue-common-types {
  yang-version 1;
  namespace "http://arista.com/yang/experimental/eos/arista-ale-counters-open-config-qos-interface-queue-common-types";
  prefix "arista-ale-counters-open-config-qos-interface-queue-common-types";
  
  import openconfig-extensions { prefix "oc-ext"; }
  import openconfig-interfaces { prefix "openconfig-interfaces"; }
  
  organization
    "Arista Networks <http://arista.com/>";
  contact
    "Arista Networks <http://arista.com/>";
  
  description
    "Common types for OpenConfig QoS interface queue counters.
    THIS YANG MODULE WAS GENERATED. DO NOT EDIT THIS FILE.";
  
  oc-ext:openconfig-version "1.0.0";
  
  revision "2026-04-15" {
    description
      "Version 1.0.0, generated on 2026-04-15";
    reference "1.0.0";
  }
  grouping ale-counters-open-config-interface-queue-key {
    leaf interface-id {
      type openconfig-interfaces:interface-id;
      description
        "interface-id";
    }
    leaf name {
      type string;
      description
        "name";
    }
    description
      "Key identifying a QoS interface queue by interface and queue name.";
  }
} // main-yang
