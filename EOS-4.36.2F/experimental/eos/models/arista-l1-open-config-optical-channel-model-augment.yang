module arista-l1-open-config-optical-channel-model-augment {
  yang-version 1;
  namespace "http://arista.com/yang/arista-l1-open-config-optical-channel-model-augment";
  prefix "arista-l1-open-config-optical-channel-model-augment";
  
  import openconfig-extensions { prefix "oc-ext"; }
  import arista-l1-open-config-prbs-model { prefix "arista-l1-open-config-prbs-model"; }
  import arista-l1-open-config-xcvr-oc-types { prefix "arista-l1-open-config-xcvr-oc-types"; }
  import arista-l1-types-l1-types { prefix "arista-l1-types-l1-types"; }
  import arista-xcvr-xcvr-test-pattern { prefix "arista-xcvr-xcvr-test-pattern"; }
  import openconfig-platform { prefix "openconfig-platform"; }
  import openconfig-terminal-device { prefix "openconfig-terminal-device"; }
  import openconfig-transport-types { prefix "openconfig-transport-types"; }
  
  organization
    "Arista Networks <http://arista.com/>";
  contact
    "Arista Networks <http://arista.com/>";
  
  description
    "Attributes related to optical parameters
    THIS YANG MODULE WAS GENERATED. DO NOT EDIT THIS FILE.";
  
  oc-ext:openconfig-version "1.0.0";
  
  revision "2022-05-12" {
    description
      "Version 1.0.0, generated on 2022-05-12";
    reference "1.0.0";
  }
  grouping l1-open-config-xcvr-optical-channel-state {
    description
      "Container for the state of the optical channel";
  }
  grouping l1-open-config-xcvr-logical-channel-base-state {
    list test-pattern {
      key "lane";
      uses arista-l1-open-config-prbs-model:l1-open-config-prbs-prbs-lane-status;
      description
        "Transceiver media channel test pattern statistics per lane";
    }
    description
      "Host facing ethernet stats";
  }
  grouping l1-open-config-xcvr-logical-otn-channel-state {
    description
      "Media stats in otn container";
  }
  augment "/openconfig-platform:components/openconfig-platform:component/openconfig-terminal-device:optical-channel/openconfig-terminal-device:state" {
    container q-margin {
      uses arista-l1-open-config-xcvr-oc-types:l1-open-config-xcvr-avg-min-max-instant-stats;
      description
        "qMargin";
    }
    container snr-margin {
      uses arista-l1-open-config-xcvr-oc-types:l1-open-config-xcvr-avg-min-max-instant-stats-p2;
      description
        "snrMargin";
    }
    description
      "qMargin
      snrMargin";
  }
  augment "/openconfig-terminal-device:terminal-device/openconfig-terminal-device:logical-channels/openconfig-terminal-device:channel/openconfig-terminal-device:state" {
    list test-pattern {
      key "lane";
      uses arista-l1-open-config-prbs-model:l1-open-config-prbs-prbs-lane-status;
      description
        "Transceiver media channel test pattern statistics per lane";
    }
    description
      "testPattern";
  }
  augment "/openconfig-terminal-device:terminal-device/openconfig-terminal-device:logical-channels/openconfig-terminal-device:channel/openconfig-terminal-device:otn/openconfig-terminal-device:state" {
    container q-margin {
      uses arista-l1-open-config-xcvr-oc-types:l1-open-config-xcvr-avg-min-max-instant-stats;
      description
        "qMargin";
    }
    container snr-margin {
      uses arista-l1-open-config-xcvr-oc-types:l1-open-config-xcvr-avg-min-max-instant-stats-p2;
      description
        "snrMargin";
    }
    description
      "qMargin
      snrMargin";
  }
} // augment-yang
