module arista-classification-defined-set-open-config {
  yang-version 1;
  namespace "http://arista.com/yang/arista-classification-defined-set-open-config";
  prefix "arista-classification-defined-set-open-config";
  
  import openconfig-extensions { prefix "oc-ext"; }
  import openconfig-acl { prefix "openconfig-acl"; }
  import openconfig-inet-types { prefix "openconfig-inet-types"; }
  import openconfig-packet-match-types { prefix "openconfig-packet-match-types"; }
  
  organization
    "Arista Networks <http://arista.com/>";
  contact
    "Arista Networks <http://arista.com/>";
  
  description
    "Traffic Policy Field Sets
    THIS YANG MODULE WAS GENERATED. DO NOT EDIT THIS FILE.";
  
  oc-ext:openconfig-version "1.0.1";
  
  revision "2024-08-09" {
    description
      "Version 1.0.1, generated on 2024-08-09";
    reference "1.0.1";
  }
  // covered-by: openconfig-defined-sets.yang
  
  grouping classification-oc-field-set-oc-field-set-prefix-config {
    leaf name {
      type string;
      description
        "name";
    }
    leaf-list prefix {
      type openconfig-inet-types:ip-prefix;
      oc-ext:telemetry-atomic;
      description
        "prefix";
    }
    leaf-list exclude-prefix {
      type openconfig-inet-types:ip-prefix;
      oc-ext:telemetry-atomic;
      description
        "exclude-prefix";
    }
    description
      "classification-oc-field-set-oc-field-set-prefix-config";
  }
  grouping classification-oc-field-set-oc-ipv4-field-set-config-dir {
    leaf name {
      type string;
      description
        "name of the grouping";
    }
    description
      "";
  }
  grouping classification-oc-field-set-oc-ipv6-field-set-config-dir {
    leaf name {
      type string;
      description
        "name of the grouping";
    }
    description
      "";
  }
  grouping classification-oc-field-set-oc-ipv4-field-set-state-dir {
    leaf name {
      type string;
      description
        "name of the grouping";
    }
    description
      "";
  }
  grouping classification-oc-field-set-oc-ipv6-field-set-state-dir {
    leaf name {
      type string;
      description
        "name of the grouping";
    }
    description
      "";
  }
  grouping classification-oc-field-set-oc-field-set-port-config {
    leaf name {
      type string;
      description
        "name";
    }
    leaf-list port {
      type openconfig-packet-match-types:port-num-range;
      oc-ext:telemetry-atomic;
      description
        "port";
    }
    leaf-list exclude-port {
      type openconfig-packet-match-types:port-num-range;
      oc-ext:telemetry-atomic;
      description
        "exclude-port";
    }
    description
      "classification-oc-field-set-oc-field-set-port-config";
  }
  grouping classification-oc-field-set-oc-port-field-set-config-dir {
    leaf name {
      type string;
      description
        "name of the grouping";
    }
    description
      "";
  }
  grouping classification-oc-field-set-oc-port-field-set-state-dir {
    leaf name {
      type string;
      description
        "name of the grouping";
    }
    description
      "";
  }
  container defined-sets {
    container ipv4-prefix-sets {
      list ipv4-prefix-set {
        key "name";
        oc-ext:telemetry-atomic;
        leaf name {
          type string;
          description
            "name leaf used as key for ipv4-prefix-set list";
        }
        container config {
          uses classification-oc-field-set-oc-field-set-prefix-config;
          description
            "config container";
        }
        container state {
          uses classification-oc-field-set-oc-field-set-prefix-config;
          config false;
          description
            "state container";
        }
        description
          "ipv4-prefix-set list";
      }
      oc-ext:telemetry-atomic;
      description
        "ipv4-prefix-sets container";
    }
    container ipv6-prefix-sets {
      list ipv6-prefix-set {
        key "name";
        oc-ext:telemetry-atomic;
        leaf name {
          type string;
          description
            "name leaf used as key for ipv6-prefix-set list";
        }
        container config {
          uses classification-oc-field-set-oc-field-set-prefix-config;
          description
            "config container";
        }
        container state {
          uses classification-oc-field-set-oc-field-set-prefix-config;
          config false;
          description
            "state container";
        }
        description
          "ipv6-prefix-set list";
      }
      oc-ext:telemetry-atomic;
      description
        "ipv6-prefix-sets container";
    }
    container port-sets {
      list port-set {
        key "name";
        oc-ext:telemetry-atomic;
        leaf name {
          type string;
          description
            "name leaf used as key for port-set list";
        }
        container config {
          uses classification-oc-field-set-oc-field-set-port-config;
          description
            "config container";
        }
        container state {
          uses classification-oc-field-set-oc-field-set-port-config;
          config false;
          description
            "state container";
        }
        description
          "port-set list";
      }
      oc-ext:telemetry-atomic;
      description
        "port-sets container";
    }
    oc-ext:telemetry-atomic;
    description
      "defined-sets container";
  }
} // main-yang
