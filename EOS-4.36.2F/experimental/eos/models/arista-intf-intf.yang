module arista-intf-intf {
  yang-version 1;
  namespace "http://arista.com/yang/experimental/eos/arista-intf-intf";
  prefix "arista-intf-intf";
  
  import openconfig-extensions { prefix "oc-ext"; }
  import arista-arnet-rate { prefix "arista-arnet-rate"; }
  
  organization
    "Arista Networks <http://arista.com/>";
  contact
    "Arista Networks <http://arista.com/>";
  
  description
    "Defines interface rates
    THIS YANG MODULE WAS GENERATED. DO NOT EDIT THIS FILE.";
  
  oc-ext:openconfig-version "0.1.0";
  
  revision "2023-08-15" {
    description
      "Version 0.1.0, generated on 2023-08-15";
    reference "0.1.0";
  }
  grouping interface-intf-statistics {
    leaf out-unicast-pkts {
      type uint64;
      description
        "out-ucast-pkts";
    }
    leaf out-multicast-pkts {
      type uint64;
      description
        "out-multicast-pkts";
    }
    leaf out-broadcast-pkts {
      type uint64;
      description
        "out-broadcast-pkts";
    }
    leaf in-unicast-pkts {
      type uint64;
      description
        "in-ucast-pkts";
    }
    leaf in-multicast-pkts {
      type uint64;
      description
        "in-multicast-pkts";
    }
    leaf in-broadcast-pkts {
      type uint64;
      description
        "in-broadcast-pkts";
    }
    leaf in-octets {
      type uint64;
      description
        "in-octets";
    }
    leaf in-discards {
      type uint64;
      description
        "in-discards";
    }
    leaf in-errors {
      type uint64;
      description
        "in-errors";
    }
    leaf out-errors {
      type uint64;
      description
        "out-errors";
    }
    leaf in-pkts {
      type uint64;
      description
        "in-pkts-gnmi";
    }
    leaf out-pkts {
      type uint64;
      description
        "out-pkts-gnmi";
    }
    leaf out-octets {
      type uint64;
      description
        "out-octets64";
    }
    leaf out-discards {
      type uint64;
      description
        "out-discards64";
    }
    description
      "interface-intf-statistics";
  }
  grouping interface-intf-rates {
    leaf out-pkts-rate {
      type arista-arnet-rate:arnet-packets-per-second;
      description
        "";
    }
    leaf in-pkts-rate {
      type arista-arnet-rate:arnet-packets-per-second;
      description
        "";
    }
    leaf out-bits-rate {
      type arista-arnet-rate:arnet-bits-per-second;
      description
        "";
    }
    leaf in-bits-rate {
      type arista-arnet-rate:arnet-bits-per-second;
      description
        "";
    }
    leaf out-pkts-inst-rate {
      type arista-arnet-rate:arnet-packets-per-second;
      description
        "";
    }
    leaf in-pkts-inst-rate {
      type arista-arnet-rate:arnet-packets-per-second;
      description
        "";
    }
    leaf out-bits-inst-rate {
      type arista-arnet-rate:arnet-bits-per-second;
      description
        "";
    }
    leaf in-bits-inst-rate {
      type arista-arnet-rate:arnet-bits-per-second;
      description
        "";
    }
    description
      "";
  }
} // main-yang
