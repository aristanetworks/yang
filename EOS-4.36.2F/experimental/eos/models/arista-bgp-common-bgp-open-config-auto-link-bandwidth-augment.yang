module arista-bgp-common-bgp-open-config-auto-link-bandwidth-augment {
  yang-version 1;
  namespace "http://arista.com/yang/arista-bgp-common-bgp-open-config-auto-link-bandwidth-augment";
  prefix "arista-bgp-common-bgp-open-config-auto-link-bandwidth-augment";
  
  import openconfig-extensions { prefix "oc-ext"; }
  import openconfig-bgp-types { prefix "openconfig-bgp-types"; }
  import openconfig-network-instance { prefix "openconfig-network-instance"; }
  
  organization
    "Arista Networks <http://arista.com/>";
  contact
    "Arista Networks <http://arista.com/>";
  
  description
    "TAC models for OC BGP 'auto-link-bandwidth' paths
    THIS YANG MODULE WAS GENERATED. DO NOT EDIT THIS FILE.";
  
  oc-ext:openconfig-version "9.9.1";
  
  revision "2025-09-22" {
    description
      "Version 9.9.1, generated on 2025-09-22";
    reference "9.9.1";
  }
  grouping routing-bgp-open-config-ocauto-link-bandwidth-config {
    leaf percentage {
      type decimal64 {
        fraction-digits 2;
      }
      description
        "Configure the percentage of the underlying interface speed used to set the auto-generated link-bandwidth extended community value. This field MUST not be set if enabled is not true. If enabled is true but this field is not present, a default of 100.0 is implied.";
    }
    description
      "routing-bgp-open-config-ocauto-link-bandwidth-config";
  }
  augment "/openconfig-network-instance:network-instances/openconfig-network-instance:network-instance/openconfig-network-instance:protocols/openconfig-network-instance:protocol/openconfig-network-instance:bgp/openconfig-network-instance:neighbors/openconfig-network-instance:neighbor/openconfig-network-instance:auto-link-bandwidth/openconfig-network-instance:import/openconfig-network-instance:config" {
    leaf percentage {
      type decimal64 {
        fraction-digits 2;
      }
      description
        "Configure the percentage of the underlying interface speed used to set the auto-generated link-bandwidth extended community value. This field MUST not be set if enabled is not true. If enabled is true but this field is not present, a default of 100.0 is implied.";
    }
    description
      "";
  }
  augment "/openconfig-network-instance:network-instances/openconfig-network-instance:network-instance/openconfig-network-instance:protocols/openconfig-network-instance:protocol/openconfig-network-instance:bgp/openconfig-network-instance:neighbors/openconfig-network-instance:neighbor/openconfig-network-instance:auto-link-bandwidth/openconfig-network-instance:import/openconfig-network-instance:state" {
    leaf percentage {
      type decimal64 {
        fraction-digits 2;
      }
      description
        "Configure the percentage of the underlying interface speed used to set the auto-generated link-bandwidth extended community value. This field MUST not be set if enabled is not true. If enabled is true but this field is not present, a default of 100.0 is implied.";
    }
    description
      "";
  }
  augment "/openconfig-network-instance:network-instances/openconfig-network-instance:network-instance/openconfig-network-instance:protocols/openconfig-network-instance:protocol/openconfig-network-instance:bgp/openconfig-network-instance:peer-groups/openconfig-network-instance:peer-group/openconfig-network-instance:auto-link-bandwidth/openconfig-network-instance:import/openconfig-network-instance:config" {
    leaf percentage {
      type decimal64 {
        fraction-digits 2;
      }
      description
        "Configure the percentage of the underlying interface speed used to set the auto-generated link-bandwidth extended community value. This field MUST not be set if enabled is not true. If enabled is true but this field is not present, a default of 100.0 is implied.";
    }
    description
      "";
  }
  augment "/openconfig-network-instance:network-instances/openconfig-network-instance:network-instance/openconfig-network-instance:protocols/openconfig-network-instance:protocol/openconfig-network-instance:bgp/openconfig-network-instance:peer-groups/openconfig-network-instance:peer-group/openconfig-network-instance:auto-link-bandwidth/openconfig-network-instance:import/openconfig-network-instance:state" {
    leaf percentage {
      type decimal64 {
        fraction-digits 2;
      }
      description
        "Configure the percentage of the underlying interface speed used to set the auto-generated link-bandwidth extended community value. This field MUST not be set if enabled is not true. If enabled is true but this field is not present, a default of 100.0 is implied.";
    }
    description
      "";
  }
} // augment-yang
