module arista-l1-open-config-phy-model {
  yang-version 1;
  namespace "http://arista.com/yang/experimental/eos/arista-l1-open-config-phy-model";
  prefix "arista-l1-open-config-phy-model";
  
  import openconfig-extensions { prefix "oc-ext"; }
  import arista-l1-open-config-prbs-model { prefix "arista-l1-open-config-prbs-model"; }
  import arista-l1-types-l1-types { prefix "arista-l1-types-l1-types"; }
  import arista-xcvr-xcvr-test-pattern { prefix "arista-xcvr-xcvr-test-pattern"; }
  import openconfig-if-ethernet { prefix "openconfig-if-ethernet"; }
  import openconfig-interfaces { prefix "openconfig-interfaces"; }
  import openconfig-types { prefix "openconfig-types"; }
  
  organization
    "Arista Networks <http://arista.com/>";
  contact
    "Arista Networks <http://arista.com/>";
  
  description
    "Attributes related to interface phy components
    THIS YANG MODULE WAS GENERATED. DO NOT EDIT THIS FILE.";
  
  oc-ext:openconfig-version "1.0.0";
  
  revision "2023-12-05" {
    description
      "Version 1.0.0, generated on 2023-12-05";
    reference "1.0.0";
  }
  typedef l1-open-config-phy-phy-link-state {
    type enumeration {
      enum UNKNOWN {
        value 0;
        description
          "unknown";
      }
      enum INIT {
        value 1;
        description
          "init";
      }
      enum DETECTING_XCVR {
        value 2;
        description
          "detectingXcvr";
      }
      enum AUTONEGOTIATING {
        value 3;
        description
          "autonegotiating";
      }
      enum LINK_DOWN {
        value 4;
        description
          "linkDown";
      }
      enum LINK_UP {
        value 5;
        description
          "linkUp";
      }
      enum ERR_DISABLED {
        value 6;
        description
          "errDisabled";
      }
    }
    description
      "Link state of a phy";
  }
  grouping l1-open-config-phy-intf-phy-lane-index {
    leaf intf-name {
      type string;
      description
        "The interface name (eg, EthernetX/Y)";
    }
    leaf phy-index {
      type uint16;
      description
        "The index of the phy (0 is the phy in the ASIC)";
    }
    leaf lane {
      type uint16;
      description
        "The lane number (0 based)";
    }
    description
      "Index for a lane based phy attribute";
  }
  grouping l1-open-config-phy-intf-phy-index {
    leaf intf-name {
      type string;
      description
        "The interface name (eg, EthernetX/Y)";
    }
    leaf phy-index {
      type uint16;
      description
        "The index of the phy (0 is the phy in the ASIC)";
    }
    description
      "Index for a phy attribute";
  }
  grouping l1-open-config-phy-pcs-lane-state {
    uses l1-open-config-phy-intf-phy-lane-index;
    description
      "Lane based attributes for the physical coding sublayer";
  }
  grouping l1-open-config-phy-pcs-lane-ingress-container {
    leaf name {
      type string;
      description
        "name of the grouping";
    }
    description
      "Container for the ingress pcs lane component";
  }
  grouping l1-open-config-phy-pcs-lane-egress-container {
    leaf name {
      type string;
      description
        "name of the grouping";
    }
    description
      "Container for the egress pcs lane component";
  }
  grouping l1-open-config-phy-pcs-state {
    uses l1-open-config-phy-intf-phy-index;
    leaf error-blocks {
      type uint64;
      description
        "errorBlocks";
    }
    description
      "Attributes for the physical coding sublayer";
  }
  grouping l1-open-config-phy-pcs-ingress-container {
    leaf name {
      type string;
      description
        "name of the grouping";
    }
    description
      "Container for the ingress pcs component";
  }
  grouping l1-open-config-phy-pcs-egress-container {
    leaf name {
      type string;
      description
        "name of the grouping";
    }
    description
      "Container for the egress pcs component";
  }
  grouping l1-open-config-phy-fec-state {
    uses l1-open-config-phy-intf-phy-index;
    leaf pre-fec-ber {
      type binary {
        length 8;
      }
      description
        "preFecBer";
    }
    leaf uncorrected-codewords {
      type uint64;
      description
        "uncorrectedCodewords";
    }
    leaf corrected-symbol-rate {
      type binary {
        length 8;
      }
      description
        "correctedSymbolRate";
    }
    leaf corrected-codewords {
      type uint64;
      description
        "correctedCodewords";
    }
    description
      "Attributes for the forward error correction layer";
  }
  grouping l1-open-config-phy-eth-corrected-codewords-entry {
    leaf corrected-symbols-max {
      type uint8;
      description
        "Maximum number of corrected symbols in this bin";
    }
    description
      "Corrected codewords bin entry";
  }
  grouping l1-open-config-phy-eth-corrected-codewords-data {
    uses l1-open-config-phy-intf-phy-index;
    list bin {
      key "corrected-symbols-max";
      uses l1-open-config-phy-eth-corrected-codewords-entry;
      description
        "Bin container";
    }
    description
      "Corrected codewords container";
  }
  grouping l1-open-config-phy-fabric-corrected-codewords-entry {
    leaf corrected-symbols-max {
      type uint8;
      description
        "Maximum number of corrected symbols in this bin";
    }
    description
      "Corrected codewords bin entry";
  }
  grouping l1-open-config-phy-fabric-corrected-codewords-data {
    uses l1-open-config-phy-intf-phy-index;
    list bin {
      key "corrected-symbols-max";
      uses l1-open-config-phy-fabric-corrected-codewords-entry;
      description
        "Bin container";
    }
    description
      "Corrected codewords container";
  }
  grouping l1-open-config-phy-fec-ingress-container {
    leaf name {
      type string;
      description
        "name of the grouping";
    }
    list eth-corr-codewords {
      key "intf-name phy-index";
      uses l1-open-config-phy-eth-corrected-codewords-data;
      description
        "Corrected codewords indexed by interface and phy";
    }
    list fabric-corr-codewords {
      key "intf-name phy-index";
      uses l1-open-config-phy-fabric-corrected-codewords-data;
      description
        "Fabric corrected codewords indexed by interface and phy";
    }
    description
      "Container for the ingress FEC component";
  }
  grouping l1-open-config-phy-fec-egress-container {
    leaf name {
      type string;
      description
        "name of the grouping";
    }
    description
      "Container for the egress FEC component";
  }
  grouping l1-open-config-phy-rs-state {
    uses l1-open-config-phy-intf-phy-index;
    leaf link-state {
      type l1-open-config-phy-phy-link-state;
      description
        "linkState";
    }
    leaf last-link-state-change {
      type openconfig-types:timeticks64;
      description
        "lastLinkStateChange";
    }
    leaf remote-fault {
      type boolean;
      description
        "remoteFault";
    }
    leaf last-remote-fault-change {
      type openconfig-types:timeticks64;
      description
        "lastRemoteFaultChange";
    }
    leaf local-fault {
      type boolean;
      description
        "localFault";
    }
    leaf last-local-fault-change {
      type openconfig-types:timeticks64;
      description
        "lastLocalFaultChange";
    }
    description
      "Attributes for the Rs coding sublayer";
  }
  grouping l1-open-config-phy-phy-prbs-status {
    uses l1-open-config-phy-intf-phy-index;
    list lane {
      key "lane";
      uses arista-l1-open-config-prbs-model:l1-open-config-prbs-prbs-lane-status;
      description
        "Receive attributes collected by SerDes lane";
    }
    description
      "Entry container for a device's test pattern stats";
  }
  augment "/openconfig-interfaces:interfaces/openconfig-interfaces:interface/openconfig-if-ethernet:ethernet" {
    container phys {
      list phy {
        key "index";
        leaf index {
          type uint16;
          description
            "index leaf used as key for phy list";
        }
        container ingress {
          container pcs {
            container lanes {
              list lane {
                key "lane";
                leaf lane {
                  type uint16;
                  description
                    "lane leaf used as key for lane list";
                }
                container state {
                  uses l1-open-config-phy-pcs-lane-state;
                  config false;
                  description
                    "state container";
                }
                description
                  "lane list";
              }
              description
                "lanes container";
            }
            container state {
              uses l1-open-config-phy-pcs-state;
              config false;
              description
                "state container";
            }
            description
              "pcs container";
          }
          container fec {
            container state {
              uses l1-open-config-phy-fec-state;
              config false;
              description
                "state container";
            }
            container error-distribution {
              container bins {
                list bin {
                  key "corrected-symbols-max";
                  leaf corrected-symbols-max {
                    type string;
                    description
                      "corrected-symbols-max leaf used as key for bin list";
                  }
                  container state {
                    leaf codewords {
                      config false;
                      type uint64;
                      description
                        "Number of codewords corrected in this bin";
                    }
                    description
                      "state container";
                  }
                  description
                    "bin list";
                }
                description
                  "bins container";
              }
              description
                "error-distribution container";
            }
            description
              "fec container";
          }
          container rs {
            container state {
              uses l1-open-config-phy-rs-state;
              config false;
              description
                "state container";
            }
            description
              "rs container";
          }
          container test-pattern {
            uses l1-open-config-phy-phy-prbs-status;
            config false;
            description
              "test-pattern container";
          }
          description
            "ingress container";
        }
        container egress {
          container pcs {
            container lanes {
              list lane {
                key "lane";
                leaf lane {
                  type uint16;
                  description
                    "lane leaf used as key for lane list";
                }
                container state {
                  uses l1-open-config-phy-pcs-lane-state;
                  config false;
                  description
                    "state container";
                }
                description
                  "lane list";
              }
              description
                "lanes container";
            }
            container state {
              uses l1-open-config-phy-pcs-state;
              config false;
              description
                "state container";
            }
            description
              "pcs container";
          }
          container fec {
            container state {
              uses l1-open-config-phy-fec-state;
              config false;
              description
                "state container";
            }
            description
              "fec container";
          }
          container test-pattern {
            uses l1-open-config-phy-phy-prbs-status;
            config false;
            description
              "test-pattern container";
          }
          description
            "egress container";
        }
        description
          "phy list";
      }
      description
        "phys container";
    }
  }
  augment "/openconfig-interfaces:interfaces/openconfig-interfaces:interface" {
    container fabric {
      container phys {
        list phy {
          key "index";
          leaf index {
            type string;
            description
              "index leaf used as key for phy list";
          }
          container ingress {
            container fec {
              container error-distribution {
                container bins {
                  list bin {
                    key "corrected-symbols-max";
                    leaf corrected-symbols-max {
                      type string;
                      description
                        "corrected-symbols-max leaf used as key for bin list";
                    }
                    container state {
                      leaf codewords {
                        config false;
                        type uint64;
                        description
                          "Number of codewords corrected in this bin";
                      }
                      description
                        "state container";
                    }
                    description
                      "bin list";
                  }
                  description
                    "bins container";
                }
                description
                  "error-distribution container";
              }
              description
                "fec container";
            }
            description
              "ingress container";
          }
          description
            "phy list";
        }
        description
          "phys container";
      }
      description
        "fabric container";
    }
  }
} // main-yang
