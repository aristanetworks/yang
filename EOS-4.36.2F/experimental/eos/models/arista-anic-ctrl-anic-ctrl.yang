module arista-anic-ctrl-anic-ctrl {
  yang-version 1;
  namespace "http://arista.com/yang/experimental/eos/arista-anic-ctrl-anic-ctrl";
  prefix "arista-anic-ctrl-anic-ctrl";
  
  import openconfig-extensions { prefix "oc-ext"; }
  import arista-arnet-vrf-name { prefix "arista-arnet-vrf-name"; }
  import arista-eos-types { prefix "arista-eos-types"; }
  import arista-exp-eos { prefix "arista-exp-eos"; }
  import openconfig-inet-types { prefix "openconfig-inet-types"; }
  import openconfig-interfaces { prefix "openconfig-interfaces"; }
  
  organization
    "Arista Networks <http://arista.com/>";
  contact
    "Arista Networks <http://arista.com/>";
  
  description
    "Attached NIC aggregated config and status
    THIS YANG MODULE WAS GENERATED. DO NOT EDIT THIS FILE.";
  
  oc-ext:openconfig-version "0.0.1";
  
  revision "2025-03-10" {
    description
      "Version 0.0.1, generated on 2025-03-10";
    reference "0.0.1";
  }
  typedef anic-ctrl-anic-management-state-state-enum {
    type enumeration {
      enum NOT_CONFIGURED {
        value 0;
        description
          "NOT_CONFIGURED";
      }
      enum NOT_ACTIVE {
        value 1;
        description
          "NOT_ACTIVE";
      }
      enum CONNECTION_PENDING {
        value 2;
        description
          "CONNECTION_PENDING";
      }
      enum CONNECTION_ERROR {
        value 3;
        description
          "CONNECTION_ERROR";
      }
      enum CONNECTION_ACTIVE {
        value 4;
        description
          "CONNECTION_ACTIVE";
      }
    }
    description
      "anic-ctrl-anic-management-state-state-enum";
  }
  grouping anic-ctrl-anic-management-info {
    leaf addr {
      type openconfig-inet-types:ip-address;
      description
        "addr";
    }
    leaf host-name {
      type string;
      default "";
      description
        "host-name";
    }
    leaf vrf-name {
      type arista-arnet-vrf-name:l3-vrf-name;
      description
        "vrf-name";
    }
    leaf host-interface {
      type string;
      default "";
      description
        "host-interface";
    }
    description
      "anic-ctrl-anic-management-info";
  }
  grouping anic-ctrl-metric-path-table-key {
    leaf job-uri {
      type string;
      description
        "job-uri";
    }
    leaf vrf-name {
      type arista-arnet-vrf-name:l3-vrf-name;
      description
        "vrf-name";
    }
    leaf host-interface {
      type string;
      description
        "host-interface";
    }
    leaf table-name {
      type string;
      description
        "table-name";
    }
    leaf label {
      type string;
      description
        "label";
    }
    description
      "anic-ctrl-metric-path-table-key";
  }
  grouping anic-ctrl-anic-job-status {
    leaf name {
      type string;
      description
        "name of the grouping";
    }
    leaf job-name {
      type string;
      description
        "job-name";
    }
    container metric-path-table-key {
      uses anic-ctrl-metric-path-table-key;
      description
        "metric-path-table-key";
    }
    leaf job-uri {
      type string;
      description
        "job-uri";
    }
    leaf last-job-error {
      type string;
      description
        "last-job-error";
    }
    leaf last-metrics-update-timestamp {
      type arista-eos-types:seconds;
      description
        "last-metrics-update-timestamp";
    }
    leaf last-poll-timestamp {
      type arista-eos-types:seconds;
      description
        "last-poll-timestamp";
    }
    leaf next-poll-timestamp {
      type arista-eos-types:seconds;
      description
        "next-poll-timestamp";
    }
    description
      "anic-ctrl-anic-job-status";
  }
  grouping anic-ctrl-anic-status {
    leaf name {
      type openconfig-interfaces:interface-id;
      description
        "Interface directly connected to the NIC";
    }
    leaf anic-profile-name {
      type string;
      description
        "";
    }
    container management-state {
      uses anic-ctrl-anic-management-state;
      description
        "";
    }
    container management-info {
      uses anic-ctrl-anic-management-info;
      description
        "";
    }
    leaf connection-not-active-reason {
      type string;
      description
        "";
    }
    list job-status {
      key "job-name";
      uses anic-ctrl-anic-job-status;
      description
        "";
    }
    description
      "Status for a single attached NIC";
  }
  grouping anic-ctrl-anic-management-state {
    description
      "anic-ctrl-anic-management-state";
  }
  grouping anic-ctrl-all-anic-status {
    leaf name {
      type string;
      description
        "name of the grouping";
    }
    list interface {
      key "name";
      uses anic-ctrl-anic-status;
      description
        "Collection of statuses for all attached NICs";
    }
    description
      "Aggregated attached NIC status";
  }
  augment "/arista-exp-eos:arista" {
    container anic {
      container interfaces {
        list interface {
          key "name";
          config false;
          uses anic-ctrl-anic-status;
          description
            "interface list";
        }
        description
          "interfaces container";
      }
      description
        "anic container";
    }
  }
} // main-yang
