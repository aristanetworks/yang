module arista-latency-measurement {
  yang-version 1;
  namespace "http://arista.com/yang/experimental/eos/arista-latency-measurement";
  prefix "arista-latency-measurement";
  
  import openconfig-extensions { prefix "oc-ext"; }
  import openconfig-qos { prefix "openconfig-qos"; }
  import openconfig-types { prefix "openconfig-types"; }
  
  organization
    "Arista Networks <http://arista.com/>";
  contact
    "Arista Networks <http://arista.com/>";
  
  description
    "This module contains latency measurement augments.
    THIS YANG MODULE WAS GENERATED. DO NOT EDIT THIS FILE.";
  
  oc-ext:openconfig-version "1.0.0";
  
  revision "2025-06-30" {
    description
      "Version 1.0.0, generated on 2025-06-30";
    reference "1.0.0";
  }
  grouping ale-counters-open-config-latency-bin-state {
    leaf bin-id {
      type uint16;
      description
        "bin-id";
    }
    leaf packet-count {
      type uint64;
      description
        "Packet count in the latency bin.";
    }
    description
      "ale-counters-open-config-latency-bin-state";
  }
  grouping ale-counters-open-config-latency-bin {
    leaf bin-id {
      type uint16;
      description
        "bin-id";
    }
    container state {
      uses ale-counters-open-config-latency-bin-state;
      description
        "state";
    }
    description
      "Latency bins keeping packet counts for packets whose latency falls between the bin lower and upper bound.";
  }
  grouping ale-counters-open-config-latency-bin-container {
    list bin {
      key "bin-id";
      uses ale-counters-open-config-latency-bin;
      description
        "bin";
    }
    description
      "ale-counters-open-config-latency-bin-container";
  }
  grouping ale-counters-open-config-latency-max-state {
    leaf max-latency {
      type uint32;
      units nanoseconds;
      description
        "Maximum nanoseconds of latency observed over the most recent poll interval.";
    }
    leaf max-latency-last-update-time {
      type openconfig-types:timeticks64;
      description
        "Maximum latency last polled timestamp.";
    }
    description
      "ale-counters-open-config-latency-max-state";
  }
  grouping ale-counters-open-config-interface-traffic-class-key {
    description
      "ale-counters-open-config-interface-traffic-class-key";
  }
  grouping ale-counters-open-config-latency-container {
    uses ale-counters-open-config-interface-traffic-class-key;
    container state {
      uses ale-counters-open-config-latency-max-state;
      description
        "state";
    }
    container histogram-bins {
      uses ale-counters-open-config-latency-bin-container;
      description
        "histogram-bins";
    }
    description
      "ale-counters-open-config-latency-container";
  }
  grouping ale-counters-open-config-open-config-latency-measurement {
    leaf name {
      type string;
      description
        "name of the grouping";
    }
    description
      "ale-counters-open-config-open-config-latency-measurement";
  }
  augment "/openconfig-qos:qos/openconfig-qos:interfaces/openconfig-qos:interface/openconfig-qos:output/openconfig-qos:queues/openconfig-qos:queue" {
    container latency {
      uses ale-counters-open-config-latency-container;
      config false;
      description
        "latency container";
    }
  }
} // main-yang
