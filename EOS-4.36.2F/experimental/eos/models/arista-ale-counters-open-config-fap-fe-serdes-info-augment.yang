module arista-ale-counters-open-config-fap-fe-serdes-info-augment {
  yang-version 1;
  namespace "http://arista.com/yang/experimental/eos/arista-ale-counters-open-config-fap-fe-serdes-info-augment";
  prefix "arista-ale-counters-open-config-fap-fe-serdes-info-augment";
  
  import openconfig-extensions { prefix "oc-ext"; }
  import openconfig-platform { prefix "openconfig-platform"; }
  import openconfig-types { prefix "openconfig-types"; }
  
  organization
    "Arista Networks <http://arista.com/>";
  contact
    "Arista Networks <http://arista.com/>";
  
  description
    "Serdes information for SwitchChip and FabricChip.
    THIS YANG MODULE WAS GENERATED. DO NOT EDIT THIS FILE.";
  
  oc-ext:openconfig-version "0.0.0";
  
  revision "2024-08-22" {
    description
      "Version 0.0.0, generated on 2024-08-22";
    reference "0.0.0";
  }
  typedef ale-counters-open-config-serdes-admin-status {
    type enumeration {
      enum ADMIN_UP {
        value 0;
        description
          "UP";
      }
      enum ADMIN_DOWN {
        value 1;
        description
          "DOWN";
      }
    }
    description
      "Serdes Admin status.";
  }
  typedef ale-counters-open-config-serdes-operational-status {
    type enumeration {
      enum SERDES_UP {
        value 0;
        description
          "The link is UP.";
      }
      enum SERDES_DOWN {
        value 1;
        description
          "The link is DOWN.";
      }
      enum SERDES_ISOLATED {
        value 2;
        description
          "The link is disabled if errors exceed the threshold.";
      }
      enum SERDES_UNREACHABLE {
        value 3;
        description
          "The link is advertised as unreachable by fabric audit.";
      }
    }
    description
      "Serdes Operational status.";
  }
  grouping ale-counters-open-config-serdes-info-key {
    leaf name {
      type string;
      description
        "Chip name.";
    }
    leaf serdes-id {
      type uint64;
      description
        "Serdes Id.";
    }
    description
      "Serdes chip name and serdesId key.";
  }
  grouping ale-counters-open-config-serdes-info {
    uses ale-counters-open-config-serdes-info-key;
    leaf admin-status {
      type ale-counters-open-config-serdes-admin-status;
      description
        "Serdes Admin status.";
    }
    leaf oper-status {
      type ale-counters-open-config-serdes-operational-status;
      description
        "Serdes Operational status.";
    }
    leaf isolated-last-occurred {
      type openconfig-types:timeticks64;
      description
        "Timestamp of last operational status change to ISOLATED in UTC.";
    }
    leaf isolated-count {
      type uint64;
      description
        "Number of times the operational status changed to ISOLATED.";
    }
    leaf rx-cells {
      type uint64;
      description
        "Received cells.";
    }
    leaf tx-cells {
      type uint64;
      description
        "Transmitted cells.";
    }
    leaf tx-data-rate {
      type uint64;
      description
        "Transmit data rate in bps.";
    }
    leaf rx-control-cells {
      type uint64;
      description
        "Received control cells.";
    }
    leaf rx-data-rate {
      type uint64;
      description
        "Receive data rate in bps.";
    }
    leaf fec-cells {
      type uint64;
      description
        "FEC corrected cells.";
    }
    leaf fec-cells-last-occurred {
      type openconfig-types:timeticks64;
      description
        "Time FEC cells last occurred in UTC.";
    }
    leaf fec-corrected-bits {
      type uint64;
      description
        "FEC corrected bits.";
    }
    leaf fec-corrected-symbols {
      type uint64;
      description
        "FEC corrected symbols.";
    }
    leaf corrected-cells {
      type uint64;
      description
        "Corrected cells.";
    }
    leaf corrected-cells-last-occurred {
      type openconfig-types:timeticks64;
      description
        "Time Corrected cells last occurred in UTC.";
    }
    leaf crc-error-cells {
      type uint64;
      description
        "Cells received with CRC errors.";
    }
    leaf crc-errors-last-occurred {
      type openconfig-types:timeticks64;
      description
        "Time CRC errors last occurred in UTC.";
    }
    leaf crc-error-cells-changes {
      type uint64;
      description
        "Times CRC errors has changed.";
    }
    leaf leaky-bucket-tokens {
      type uint64;
      description
        "Tokens in Leaky Bucket which monitors serdes health.";
    }
    leaf max-in-fifo-cells {
      type uint64;
      description
        "Maximum cells In-Fifo.";
    }
    leaf max-in-fifo-last-occurred {
      type openconfig-types:timeticks64;
      description
        "Time maximum In-Fifo last occurred in UTC.";
    }
    leaf max-out-fifo-cells {
      type uint64;
      description
        "Maximum cells in Out-Fifo.";
    }
    leaf max-out-fifo-last-occurred {
      type openconfig-types:timeticks64;
      description
        "Time maximum Out-Fifo last occurred in UTC.";
    }
    leaf peer-chip-name {
      type string;
      description
        "Peer's SwitchChip/FabricChip name.";
    }
    leaf peer-serdes-id {
      type uint64;
      description
        "Peer's Serdes Id.";
    }
    leaf poll-last-occurred {
      type openconfig-types:timeticks64;
      description
        "Time serdes counters were last polled in UTC.";
    }
    description
      "Serdes information.";
  }
  grouping ale-counters-open-config-chip-serdes-info {
    leaf name {
      type string;
      description
        "name of the grouping";
    }
    description
      "FAP and Fabric serdes information.";
  }
  augment "/openconfig-platform:components/openconfig-platform:component/openconfig-platform:integrated-circuit" {
    container serdes-infos {
      list serdes-info {
        key "serdes-id";
        leaf serdes-id {
          type uint64;
          description
            "serdes-id leaf used as key for serdes-info list";
        }
        container state {
          uses ale-counters-open-config-serdes-info;
          config false;
          description
            "state container";
        }
        description
          "serdes-info list";
      }
      description
        "serdes-infos container";
    }
  }
} // main-yang
