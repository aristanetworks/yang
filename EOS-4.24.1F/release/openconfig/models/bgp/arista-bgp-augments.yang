module arista-bgp-augments {
  namespace "http://arista.com/yang/openconfig/bgp/augments";
  prefix arista-bgp-augments;

  import openconfig-network-instance {
    prefix oc-netinst;
  }
  import openconfig-routing-policy {
    prefix oc-rpol;
  }

  organization
    "Arista Networks, Inc.";
  contact
    "Arista Networks, Inc.
     Product Support";
  description
    "This module contains OpenConfig BGP deviations in Arista EOS.

     Copyright (c) 2019 Arista Networks, Inc. All rights reserved.";

  revision 2020-03-03 {
    description
      "Added route-target information.";
  }
  revision 2019-11-12 {
    description
      "Removed unneeded EVPN reference.";
  }
  revision 2019-03-15 {
    description
      "Initial Augments file.";
  }

  typedef route-target-type {
    description
      "This is a subset of oc-bgp-types:bgp-ext-community-type for
       route-targets:
        - <2b AS>:<4b value> per RFC4360 section 4
        - <4b IPv4>:<2b value> per RFC4360 section 4
        - <4b AS>:<2b value> per RFC5668 section 4";
    type union {
      type string {
        pattern '(6553[0-5]|655[0-2][0-9]|654[0-9]{2}|65[0-4][0-9]{2}'
              + '|6[0-4][0-9]{3}|[1-5][0-9]{4}|[1-9][0-9]{1,3}|[0-9]):'
              + '(429496729[0-5]|42949672[0-8][0-9]|4294967[0-1][0-9]{2}'
              + '|429496[0-6][0-9]{3}|42949[0-5][0-9]{4}|4294[0-8][0-9]{5}|'
              + '429[0-3][0-9]{6}|4[0-1][0-9]{7}|[1-3][0-9]{9}|'
              + '[1-9][0-9]{1,8}|[0-9])';
      }
      type string {
        pattern '(([0-9]|[1-9][0-9]|1[0-9][0-9]|2[0-4][0-9]|'
              + '25[0-5])\.){3}([0-9]|[1-9][0-9]|1[0-9][0-9]|'
              + '2[0-4][0-9]|25[0-5]):'
              + '(6553[0-5]|655[0-2][0-9]|654[0-9]{2}|65[0-4][0-9]{2}'
              + '|6[0-4][0-9]{3}|[1-5][0-9]{4}|[1-9][0-9]{1,3}|[0-9])';
      }
      type string {
        pattern '(429496729[0-5]|42949672[0-8][0-9]|4294967[0-1][0-9]{2}'
              + '|429496[0-6][0-9]{3}|42949[0-5][0-9]{4}|4294[0-8][0-9]{5}|'
              + '429[0-3][0-9]{6}|4[0-1][0-9]{7}|[1-3][0-9]{9}|'
              + '[1-9][0-9]{1,8}|[0-9]):'
              + '(6553[0-5]|655[0-2][0-9]|654[0-9]{2}|65[0-4][0-9]{2}'
              + '|6[0-4][0-9]{3}|[1-5][0-9]{4}|[1-9][0-9]{1,3}|[0-9])';
      }
    }
  }

  grouping route-target-config {
    description
      "Route-target configuration.";
    leaf-list import-target {
      type route-target-type;
      description
        "Import route-targets.";
    }
    leaf-list export-target {
      type route-target-type;
      description
        "Export route-targets.";
    }
    uses oc-rpol:apply-policy-config;
  }

  grouping best-paths-counters {
    leaf best-paths {
      type uint32;
      description
        "The number of best-paths advertised by the neighbor";
    }
    leaf best-ecmp-paths {
      type uint32;
      description
        "The number of best-ecmp-paths advertised by the neighbor";
    }
  }

  augment "/oc-netinst:network-instances/oc-netinst:network-instance/oc-netinst:protocols/oc-netinst:protocol"
        + "/oc-netinst:bgp/oc-netinst:global" {
    description
      "Augment the BGP global config to include route-target information";
    container evpn {
      leaf export-imported-route {
        type boolean;
        description
          "Export imported routes.";
      }
      uses route-target-config;
    }
    container vpn-ipv4 {
      uses route-target-config;
    }
    container vpn-ipv6 {
      uses route-target-config;
    }
  }

  augment "/oc-netinst:network-instances/oc-netinst:network-instance/oc-netinst:protocols/oc-netinst:protocol"
        + "/oc-netinst:bgp/oc-netinst:neighbors/oc-netinst:neighbor/oc-netinst:afi-safis/oc-netinst:afi-safi"
        + "/oc-netinst:state/oc-netinst:prefixes" {
    description
      "Augment BGP neighbor model to support per peer/afi-safi best path counters";
    uses best-paths-counters;
  }
}
