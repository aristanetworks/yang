module arista-exp-eos-mgmt {
  yang-version 1;
  namespace "http://arista.com/yang/experimental/eos/mgmt";
  prefix mgmt-exp;

  import arista-exp-eos {
    prefix eos-exp;
  }

  organization "Arista Networks <http://arista.com/>";
  description
    "Container for system management features.
     
     Copyright (c) 2016 Arista Networks, Inc. All rights reserved.";

  revision 2016-11-08 {
    description
      "Initial revision";
  }

  augment "/eos-exp:arista/eos-exp:eos" {
    container mgmt;
  }

  typedef System-ServerState {
    description
      "Configured state of a management service.";
    type enumeration {
      enum "globalDefault" {
        description
          "Use the global system default for the service.";
      }
      enum "disabled" {
        description
          "Service is disabled.";
      }
      enum "enabled" {
        description
          "Service is enabled.";
      }
    }
  }
}
