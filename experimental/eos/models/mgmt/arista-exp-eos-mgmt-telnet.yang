module arista-exp-eos-mgmt-telnet {
  yang-version 1;
  namespace "http://arista.com/yang/experimental/eos/mgmt/telnet";
  prefix telnet-exp;

  import arista-eos-types {
    prefix eos-types;
  }
  import arista-exp-eos {
    prefix eos-exp;
  }
  import arista-exp-eos-mgmt {
    prefix mgmt-exp;
  }

  organization "Arista Networks <http://arista.com/>";
  description
    "Models for the Telnet management subsystem of Arista EOS
     
     Copyright (c) 2016 Arista Networks, Inc. All rights reserved.";

  revision 2016-11-08 {
    description
      "Initial revision";
  }

  augment "/eos-exp:arista/eos-exp:eos/mgmt-exp:mgmt" {
    container telnet {
      description
        "Telnet management subsystem config and state.";
      container config {
        description
          "Configuration for the Telnet management subsystem.";
        uses Mgmt-Telnet-Config;
      }
    }
  }

  grouping Mgmt-Telnet-Config {
    description
      "Configuration for the Telnet management subsystem.";
    leaf idleTimeout {
      type eos-types:double;
      description
        "Telnet session timeout, in seconds.
         0 represents that session timeouts are disabled.
         
         Equivalent to the 'idle-timeout TIMEOUT' CLI command in
         the 'management telnet' config mode.";
    }
    leaf serverState {
      type mgmt-exp:System-ServerState;
      description
        "Configured enable state of the telnet management service.
         
         Equivalent to the '[ no | default ] shutdown' CLI command
         in the 'management telnet' config mode.";
    }
  }
}
