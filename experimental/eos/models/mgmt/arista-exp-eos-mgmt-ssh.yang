module arista-exp-eos-mgmt-ssh {
  yang-version 1;
  namespace "http://arista.com/yang/experimental/eos/mgmt/ssh";
  prefix ssh;

  import arista-eos-types {
    prefix eos-types;
  }
  import arista-exp-eos {
    prefix eos-exp;
  }
  import arista-exp-eos-mgmt {
    prefix mgmt-exp;
  }

  organization "Arista Networks <http://arista.com/>";
  description
    "Models for the ssh management subsystem of Arista EOS
     
     Copyright (c) 2016 Arista Networks, Inc. All rights reserved.";

  revision 2016-11-08 {
    description
      "Initial revision";
  }

  augment "/eos-exp:arista/eos-exp:eos/mgmt-exp:mgmt" {
    container ssh {
      description
        "SSH management subsystem config and state.";
      container config {
        description
          "Configuration for the SSH management subsystem.";
        uses Mgmt-Ssh-Config;
      }
    }
  }

  grouping Mgmt-Ssh-Config {
    description
      "Type: Mgmt::Ssh::Config";
    leaf idleTimeout {
      type eos-types:double;
      description
        "SSH session timeout, in seconds.
         0 represents that session timeouts are disabled.
         
         Equivalent to the 'idle-timeout TIMEOUT' CLI command in
         the 'management ssh' config mode.";
    }
    leaf serverState {
      type mgmt-exp:System-ServerState;
      description
        "Configured enable state of the SSH management service.
         
         Equivalent to the '[ no | default ] shutdown' CLI command
         in the 'management ssh' config mode.";
    }
  }
}
