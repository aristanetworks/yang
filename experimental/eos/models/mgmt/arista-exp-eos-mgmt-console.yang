module arista-exp-eos-mgmt-console {
  yang-version 1;
  namespace "http://arista.com/yang/experimental/eos/mgmt/console";
  prefix console-exp;

  import arista-eos-types {
    prefix eos-types;
  }
  import arista-exp-eos {
    prefix eos-exp;
  }
  import arista-exp-eos-mgmt {
    prefix mgmt-exp;
  }

  organization "Arista Networks <http://arista.com/>";
  description
    "Models for the console management subsystem of Arista EOS
     
     Copyright (c) 2016 Arista Networks, Inc. All rights reserved.";

  revision 2016-11-08 {
    description
      "Initial revision";
  }

  augment "/eos-exp:arista/eos-exp:eos/mgmt-exp:mgmt" {
    container console {
      description
        "Console management subsystem config and state.";
      container config {
        description
          "Configuration for the console management subsystem.";
        uses Mgmt-Console-Config;
      }
    }
  }

  grouping Mgmt-Console-Config {
    description
      "Configuration for the console management subsystem.";
    leaf idleTimeout {
      type eos-types:double;
      description
        "Console session timeout, in seconds.
         0 represents that session timeouts are disabled.
         
         Equivalent to the 'idle-timeout TIMEOUT' CLI command in
         the 'management console' config mode.";
    }
  }
}
