module arista-arnet-ip {
  yang-version 1;
  namespace "http://arista.com/yang/experimental/eos/arista-arnet-ip";
  prefix "arista-arnet-ip";

  import openconfig-extensions { prefix "oc-ext"; }
  import openconfig-inet-types { prefix "openconfig-inet-types"; }
  organization
    "Arista Networks <http://arista.com/>";
  contact
    "Arista Networks <http://arista.com/>";
  description
    "Yang model for Internet Protocol types

    THIS YANG MODULE WAS GENERATED. DO NOT EDIT THIS FILE.";

  oc-ext:openconfig-version "1.0.0";

  revision "2022-03-28" {
    description
      "Version 1.0.0, generated on 2022-03-28";
    reference "1.0.0";
  }

  grouping ip-and-port {
    leaf ip {
      type openconfig-inet-types:ipv4-address;
      description
        "IPv4 address of the connection.";
    }
    leaf port {
      type openconfig-inet-types:port-number;
      description
        "Port of the connection.";
    }
    description
      "Helps to identify a connection by holding an IPv4 address with a port number
      used by transport protocol such as TCP or UDP.";
  }
}
