module arista-acl-acl-open-config-augment {
  yang-version 1;
  namespace "http://arista.com/yang/experimental/eos/arista-acl-acl-open-config-augment";
  prefix "arista-acl-acl-open-config-augment";
  
  import openconfig-extensions { prefix "oc-ext"; }
  import openconfig-icmpv4-types { prefix "openconfig-icmpv4-types"; }
  import openconfig-icmpv6-types { prefix "openconfig-icmpv6-types"; }
  import openconfig-inet-types { prefix "openconfig-inet-types"; }
  import openconfig-packet-match-types { prefix "openconfig-packet-match-types"; }
  import openconfig-yang-types { prefix "openconfig-yang-types"; }
  import openconfig-acl { prefix "openconfig-acl"; }
  organization
    "Arista Networks <http://arista.com/>";
  contact
    "Arista Networks <http://arista.com/>";
  description
    "External tac model for traffic policy
    
    THIS YANG MODULE WAS GENERATED FROM /src/Acl/AclOpenConfig.tac.
    
    DO NOT EDIT THIS FILE.";
  
  oc-ext:openconfig-version "1.0.0";
  
  revision "2024-07-19" {
    description
      "Version 1.0.0, generated on 2024-07-19";
    reference "1.0.0";
  }
  
  typedef acl-open-config-oc-acl-cpu-ip-traffic {
    type enumeration {
      enum UNICAST {
        value 0;
        description
          "Match on unicast traffic destined to CPU";
      }
    }
    description
      "Traffic Policy match on CPU traffic options";
  }
  
  typedef acl-open-config-oc-acl-prefix-match-mode {
    type enumeration {
      enum ORDERED {
        value 0;
        description
          "Ordered by sequence-id";
      }
      enum LPM {
        value 1;
        description
          "Longest Prefix Match";
      }
    }
    description
      "Traffic Policy prefix match mode";
  }
  
  typedef acl-open-config-ocacl-mode {
    type enumeration {
      enum STATIC {
        value 0;
        description
          "Traffic policy config is added to the running-config";
      }
      enum CONTROLLER {
        value 1;
        description
          "Traffic Policy config populated by controller that isnon-persistent across reloads";
      }
    }
    description
      "Traffic Policy config mode";
  }
  
  typedef acl-open-config-counter-action {
    type enumeration {
      enum COUNT_NONE {
        value 0;
        description
          "No counter for the acl-entry ";
      }
      enum COUNT {
        value 1;
        description
          "Counter enabled for the acl-entry ";
      }
    }
    description
      "acl-open-config-counter-action";
  }
  
  grouping acl-open-config-ocacl-key {
    description
      "acl-open-config-ocacl-key";
  }
  
  grouping acl-open-config-ocacl-l2-config {
    description
      "acl-open-config-ocacl-l2-config";
  }
  
  grouping acl-open-config-ocacl-l2 {
    description
      "acl-open-config-ocacl-l2";
  }
  
  grouping acl-open-config-ocacl-icmpv4-config {
    description
      "acl-open-config-ocacl-icmpv4-config";
  }
  
  grouping acl-open-config-ocacl-icmpv4 {
    description
      "acl-open-config-ocacl-icmpv4";
  }
  
  grouping acl-open-config-ocacl-ip-common-config {
    leaf cpu-traffic {
      type acl-open-config-oc-acl-cpu-ip-traffic;
      description
        "Match on traffic destined to CPU";
    }
    description
      "acl-open-config-ocacl-ip-common-config";
  }
  
  augment "/openconfig-acl:acl/openconfig-acl:acl-sets/openconfig-acl:acl-set/openconfig-acl:acl-entries/openconfig-acl:acl-entry/openconfig-acl:ipv4/openconfig-acl:config" {
    leaf cpu-traffic {
      type acl-open-config-oc-acl-cpu-ip-traffic;
      description
        "Match on traffic destined to CPU";
    }
    description
      "To CPU Traffic";
  }
  augment "/openconfig-acl:acl/openconfig-acl:acl-sets/openconfig-acl:acl-set/openconfig-acl:acl-entries/openconfig-acl:acl-entry/openconfig-acl:ipv4/openconfig-acl:state" {
    leaf cpu-traffic {
      type acl-open-config-oc-acl-cpu-ip-traffic;
      description
        "Match on traffic destined to CPU";
    }
    description
      "To CPU Traffic";
  }
  augment "/openconfig-acl:acl/openconfig-acl:acl-sets/openconfig-acl:acl-set/openconfig-acl:acl-entries/openconfig-acl:acl-entry/openconfig-acl:ipv6/openconfig-acl:config" {
    leaf cpu-traffic {
      type acl-open-config-oc-acl-cpu-ip-traffic;
      description
        "Match on traffic destined to CPU";
    }
    description
      "To CPU Traffic";
  }
  augment "/openconfig-acl:acl/openconfig-acl:acl-sets/openconfig-acl:acl-set/openconfig-acl:acl-entries/openconfig-acl:acl-entry/openconfig-acl:ipv6/openconfig-acl:state" {
    leaf cpu-traffic {
      type acl-open-config-oc-acl-cpu-ip-traffic;
      description
        "Match on traffic destined to CPU";
    }
    description
      "To CPU Traffic";
  }
  grouping acl-open-config-ocacl-ipv4-config {
    uses acl-open-config-ocacl-ip-common-config;
    description
      "acl-open-config-ocacl-ipv4-config";
  }
  
  grouping acl-open-config-ocacl-ipv4 {
    description
      "acl-open-config-ocacl-ipv4";
  }
  
  grouping acl-open-config-ocacl-icmpv6-config {
    description
      "acl-open-config-ocacl-icmpv6-config";
  }
  
  grouping acl-open-config-ocacl-icmpv6 {
    description
      "acl-open-config-ocacl-icmpv6";
  }
  
  grouping acl-open-config-ocacl-ipv6-config {
    uses acl-open-config-ocacl-ip-common-config;
    description
      "acl-open-config-ocacl-ipv6-config";
  }
  
  grouping acl-open-config-ocacl-ipv6 {
    description
      "acl-open-config-ocacl-ipv6";
  }
  
  grouping acl-open-config-ocacl-transport-config {
    leaf-list source-port-list {
      type openconfig-packet-match-types:port-num-range;
      oc-ext:telemetry-atomic;
      description
        "List of oc-pkt-match-types:port-num-range to match the source port";
    }
    leaf-list destination-port-list {
      type openconfig-packet-match-types:port-num-range;
      oc-ext:telemetry-atomic;
      description
        "List of oc-pkt-match-types:port-num-range to match the destination port";
    }
    description
      "acl-open-config-ocacl-transport-config";
  }
  
  augment "/openconfig-acl:acl/openconfig-acl:acl-sets/openconfig-acl:acl-set/openconfig-acl:acl-entries/openconfig-acl:acl-entry/openconfig-acl:transport/openconfig-acl:config" {
    leaf-list source-port-list {
      type openconfig-packet-match-types:port-num-range;
      oc-ext:telemetry-atomic;
      description
        "List of oc-pkt-match-types:port-num-range to match the source port";
    }
    leaf-list destination-port-list {
      type openconfig-packet-match-types:port-num-range;
      oc-ext:telemetry-atomic;
      description
        "List of oc-pkt-match-types:port-num-range to match the destination port";
    }
    description
      "source port list
      destination port list";
  }
  augment "/openconfig-acl:acl/openconfig-acl:acl-sets/openconfig-acl:acl-set/openconfig-acl:acl-entries/openconfig-acl:acl-entry/openconfig-acl:transport/openconfig-acl:state" {
    leaf-list source-port-list {
      type openconfig-packet-match-types:port-num-range;
      oc-ext:telemetry-atomic;
      description
        "List of oc-pkt-match-types:port-num-range to match the source port";
    }
    leaf-list destination-port-list {
      type openconfig-packet-match-types:port-num-range;
      oc-ext:telemetry-atomic;
      description
        "List of oc-pkt-match-types:port-num-range to match the destination port";
    }
    description
      "source port list
      destination port list";
  }
  grouping acl-open-config-ocacl-transport {
    description
      "acl-open-config-ocacl-transport";
  }
  
  grouping acl-open-config-counter {
    leaf count-action {
      type acl-open-config-counter-action;
      default COUNT_NONE;
      description
        "No counter for the acl-entry ";
    }
    description
      "Add a counter on an acl-entry ";
  }
  
  grouping acl-open-config-ocacl-actions-config {
    container counter {
      uses acl-open-config-counter;
      description
        "counter";
    }
    description
      "acl-open-config-ocacl-actions-config";
  }
  
  augment "/openconfig-acl:acl/openconfig-acl:acl-sets/openconfig-acl:acl-set/openconfig-acl:acl-entries/openconfig-acl:acl-entry/openconfig-acl:actions/openconfig-acl:config" {
    container counter {
      uses acl-open-config-counter;
      description
        "counter";
    }
    description
      "counter";
  }
  augment "/openconfig-acl:acl/openconfig-acl:acl-sets/openconfig-acl:acl-set/openconfig-acl:acl-entries/openconfig-acl:acl-entry/openconfig-acl:actions/openconfig-acl:state" {
    container counter {
      uses acl-open-config-counter;
      description
        "counter";
    }
    description
      "counter";
  }
  grouping acl-open-config-ocacl-actions {
    description
      "acl-open-config-ocacl-actions";
  }
  
  grouping acl-open-config-ocacl-entry-config {
    leaf rule-name {
      type string;
      description
        "Traffic Policy rule name";
    }
    description
      "acl-open-config-ocacl-entry-config";
  }
  
  augment "/openconfig-acl:acl/openconfig-acl:acl-sets/openconfig-acl:acl-set/openconfig-acl:acl-entries/openconfig-acl:acl-entry/openconfig-acl:config" {
    leaf rule-name {
      type string;
      description
        "Traffic Policy rule name";
    }
    description
      "traffic-policy rule name";
  }
  augment "/openconfig-acl:acl/openconfig-acl:acl-sets/openconfig-acl:acl-set/openconfig-acl:acl-entries/openconfig-acl:acl-entry/openconfig-acl:state" {
    leaf rule-name {
      type string;
      description
        "Traffic Policy rule name";
    }
    description
      "traffic-policy rule name";
  }
  grouping acl-open-config-ocacl-entry {
    description
      "acl-open-config-ocacl-entry";
  }
  
  grouping acl-open-config-ocacl-entries {
    description
      "acl-open-config-ocacl-entries";
  }
  
  grouping acl-open-config-ocacl-set-config {
    leaf mode {
      type acl-open-config-ocacl-mode;
      default STATIC;
      description
        "mode";
    }
    description
      "acl-open-config-ocacl-set-config";
  }
  
  augment "/openconfig-acl:acl/openconfig-acl:acl-sets/openconfig-acl:acl-set/openconfig-acl:config" {
    leaf mode {
      type acl-open-config-ocacl-mode;
      default STATIC;
      description
        "mode";
    }
    description
      "traffic-policy mode";
  }
  augment "/openconfig-acl:acl/openconfig-acl:acl-sets/openconfig-acl:acl-set/openconfig-acl:state" {
    leaf mode {
      type acl-open-config-ocacl-mode;
      default STATIC;
      description
        "mode";
    }
    description
      "traffic-policy mode";
  }
  grouping acl-open-config-ocacl-set {
    description
      "acl-open-config-ocacl-set";
  }
  
  grouping acl-open-config-ocacl-sets {
    description
      "";
  }
  
  grouping acl-open-config-ocacl-state {
    description
      "";
  }
  
  grouping acl-open-config-ocacl-config {
    leaf prefix-match-mode {
      type acl-open-config-oc-acl-prefix-match-mode;
      default ORDERED;
      description
        "prefix-match-mode";
    }
    description
      "";
  }
  
  augment "/openconfig-acl:acl/openconfig-acl:config" {
    leaf prefix-match-mode {
      type acl-open-config-oc-acl-prefix-match-mode;
      default ORDERED;
      description
        "prefix-match-mode";
    }
    description
      "traffic-policy prefix match mode";
  }
} // augmented-yang
