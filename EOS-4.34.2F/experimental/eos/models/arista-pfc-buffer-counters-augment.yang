module arista-pfc-buffer-counters-augment {
  yang-version 1;
  namespace "http://arista.com/yang/experimental/eos/arista-pfc-buffer-counters-augment";
  prefix "arista-pfc-buffer-counters-augment";
  
  import openconfig-extensions { prefix "oc-ext"; }
  import arista-intf-augments { prefix "arista-intf-augments"; }
  import openconfig-if-ethernet { prefix "openconfig-if-ethernet"; }
  import openconfig-interfaces { prefix "openconfig-interfaces"; }
  import openconfig-types { prefix "openconfig-types"; }
  organization
    "Arista Networks <http://arista.com/>";
  contact
    "Arista Networks <http://arista.com/>";
  description
    "This module contains priority-flow-control (PFC) buffer counters.
    
    THIS YANG MODULE WAS GENERATED FROM /src/AleCounters/OpenConfigPfcBufferCounters.tac.
    
    DO NOT EDIT THIS FILE.";
  
  oc-ext:openconfig-version "1.0.0";
  
  revision "2024-12-11" {
    description
      "Version 1.0.0, generated on 2024-12-11";
    reference "1.0.0";
  }
  
  grouping ale-counters-open-config-pfc-buffer-counter-key {
    description
      "ale-counters-open-config-pfc-buffer-counter-key";
  }
  
  grouping ale-counters-open-config-pfc-buffer-counter {
    leaf dropped-pkts {
      type uint64;
      description
        "The total number of packets dropped due to PFC buffer congestion.";
    }
    leaf dropped-octets {
      type uint64;
      description
        "The total number of octets dropped due to PFC buffer congestion.";
    }
    leaf all-buffers-octets-max-last-poll {
      type uint64;
      description
        "Tracks the maximum SRAM + DRAM buffer usage in octets over the most recent polling interval.";
    }
    leaf on-chip-buffers-count-max-last-poll {
      type uint64;
      description
        "Tracks the maximum on-chip buffers count over the most recent polling interval.";
    }
    leaf on-chip-packet-descriptors-max-last-poll {
      type uint64;
      description
        "Tracks the maximum on-chip packet descriptors count over the most recent polling interval.";
    }
    leaf last-update-time {
      type openconfig-types:timeticks64;
      description
        "UTC timestamp of the last time any attribute changed";
    }
    description
      "ale-counters-open-config-pfc-buffer-counter";
  }
  
  augment "/openconfig-interfaces:interfaces/openconfig-interfaces:interface/openconfig-if-ethernet:ethernet/arista-intf-augments:pfc/arista-intf-augments:priorities/arista-intf-augments:priority/arista-intf-augments:state" {
    leaf dropped-pkts {
      type uint64;
      description
        "The total number of packets dropped due to PFC buffer congestion.";
    }
    leaf dropped-octets {
      type uint64;
      description
        "The total number of octets dropped due to PFC buffer congestion.";
    }
    leaf all-buffers-octets-max-last-poll {
      type uint64;
      description
        "Tracks the maximum SRAM + DRAM buffer usage in octets over the most recent polling interval.";
    }
    leaf on-chip-buffers-count-max-last-poll {
      type uint64;
      description
        "Tracks the maximum on-chip buffers count over the most recent polling interval.";
    }
    leaf on-chip-packet-descriptors-max-last-poll {
      type uint64;
      description
        "Tracks the maximum on-chip packet descriptors count over the most recent polling interval.";
    }
    leaf last-update-time {
      type openconfig-types:timeticks64;
      description
        "UTC timestamp of the last time any attribute changed";
    }
    description
      "The total number of packets dropped due to PFC buffer congestion.
      The total number of octets dropped due to PFC buffer congestion.
      Tracks the maximum SRAM + DRAM buffer usage in octets over the most recent polling interval.
      Tracks the maximum on-chip buffers count over the most recent polling interval.
      Tracks the maximum on-chip packet descriptors count over the most recent polling interval.
      UTC timestamp of the last time any attribute changed.";
  }
  grouping ale-counters-open-config-interface-pfc-buffer-counters {
    description
      "ale-counters-open-config-interface-pfc-buffer-counters";
  }
  
} // augmented-yang
