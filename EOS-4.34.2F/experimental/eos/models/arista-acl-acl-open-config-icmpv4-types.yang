module arista-acl-acl-open-config-icmpv4-types {
  yang-version 1;
  namespace "http://arista.com/yang/experimental/eos/arista-acl-acl-open-config-icmpv4-types";
  prefix "arista-acl-acl-open-config-icmpv4-types";
  
  import openconfig-extensions { prefix "oc-ext"; }
  organization
    "Arista Networks <http://arista.com/>";
  contact
    "Arista Networks <http://arista.com/>";
  description
    "Identity types relating to icmpv4
    
    THIS YANG MODULE WAS GENERATED FROM /src/Acl/AclOpenConfigIcmpv4Types.tac.
    
    DO NOT EDIT THIS FILE.";
  
  oc-ext:openconfig-version "1.0.0";
  
  revision "2024-07-19" {
    description
      "Version 1.0.0, generated on 2024-07-19";
    reference "1.0.0";
  }
  
  // covered-by: openconfig-icmpv4-types.yang
  identity OCICMPV4_TYPE {
    description
      "ocicmpv4-type";
  }
  identity ECHO_REPLY {
    base "OCICMPV4_TYPE";
    description
      "ECHO_REPLY";
  }
  identity DST_UNREACHABLE {
    base "OCICMPV4_TYPE";
    description
      "DST_UNREACHABLE";
  }
  identity REDIRECT {
    base "OCICMPV4_TYPE";
    description
      "REDIRECT";
  }
  identity ECHO {
    base "OCICMPV4_TYPE";
    description
      "ECHO";
  }
  identity ROUTER_ADVERTISEMENT {
    base "OCICMPV4_TYPE";
    description
      "ROUTER_ADVERTISEMENT";
  }
  identity ROUTER_SOLICITATION {
    base "OCICMPV4_TYPE";
    description
      "ROUTER_SOLICITATION";
  }
  identity TIME_EXCEEDED {
    base "OCICMPV4_TYPE";
    description
      "TIME_EXCEEDED";
  }
  identity PARAM_PROBLEM {
    base "OCICMPV4_TYPE";
    description
      "PARAM_PROBLEM";
  }
  identity TIMESTAMP {
    base "OCICMPV4_TYPE";
    description
      "TIMESTAMP";
  }
  identity TIMESTAMP_REPLY {
    base "OCICMPV4_TYPE";
    description
      "TIMESTAMP_REPLY";
  }
  identity TRACEROUTE {
    base "OCICMPV4_TYPE";
    description
      "TRACEROUTE";
  }
  identity PHOTURIS {
    base "OCICMPV4_TYPE";
    description
      "PHOTURIS";
  }
  identity EXT_ECHO_REQUEST {
    base "OCICMPV4_TYPE";
    description
      "EXT_ECHO_REQUEST";
  }
  identity EXT_ECHO_REPLY {
    base "OCICMPV4_TYPE";
    description
      "EXT_ECHO_REPLY";
  }
  identity OCICMPV4_CODE {
    description
      "ocicmpv4-code";
  }
  identity ECHO_REPLY_NONE {
    base "OCICMPV4_CODE";
    description
      "ECHO_REPLY_NONE";
  }
  identity DST_UNREACHABLE_NET {
    base "OCICMPV4_CODE";
    description
      "DST_UNREACHABLE_NET";
  }
  identity DST_UNREACHABLE_HOST {
    base "OCICMPV4_CODE";
    description
      "DST_UNREACHABLE_HOST";
  }
  identity DST_UNREACHABLE_PROTOCOL {
    base "OCICMPV4_CODE";
    description
      "DST_UNREACHABLE_PROTOCOL";
  }
  identity DST_UNREACHABLE_PORT {
    base "OCICMPV4_CODE";
    description
      "DST_UNREACHABLE_PORT";
  }
  identity DST_UNREACHABLE_CANNOT_FRAGMENT {
    base "OCICMPV4_CODE";
    description
      "DST_UNREACHABLE_CANNOT_FRAGMENT";
  }
  identity DST_UNREACHABLE_SRC_ROUTE_FAILED {
    base "OCICMPV4_CODE";
    description
      "DST_UNREACHABLE_SRC_ROUTE_FAILED";
  }
  identity DST_UNREACHABLE_DST_NET_UNKNOWN {
    base "OCICMPV4_CODE";
    description
      "DST_UNREACHABLE_DST_NET_UNKNOWN";
  }
  identity DST_UNREACHABLE_DST_HOST_UNKNOWN {
    base "OCICMPV4_CODE";
    description
      "DST_UNREACHABLE_DST_HOST_UNKNOWN";
  }
  identity DST_UNREACHABLE_SRC_HOST_ISOLATED {
    base "OCICMPV4_CODE";
    description
      "DST_UNREACHABLE_SRC_HOST_ISOLATED";
  }
  identity DST_UNREACHABLE_DST_NET_ADMIN_PROHIBITED {
    base "OCICMPV4_CODE";
    description
      "DST_UNREACHABLE_DST_NET_ADMIN_PROHIBITED";
  }
  identity DST_UNREACHABLE_DST_HOST_ADMIN_PROHIBITED {
    base "OCICMPV4_CODE";
    description
      "DST_UNREACHABLE_DST_HOST_ADMIN_PROHIBITED";
  }
  identity DST_UNREACHABLE_NET_UNREACHABLE_FOR_TOS {
    base "OCICMPV4_CODE";
    description
      "DST_UNREACHABLE_NET_UNREACHABLE_FOR_TOS";
  }
  identity DST_UNREACHABLE_HOST_UNREACHABLE_FOR_TOS {
    base "OCICMPV4_CODE";
    description
      "DST_UNREACHABLE_HOST_UNREACHABLE_FOR_TOS";
  }
  identity DST_UNREACHABLE_ADMIN_PROHIBITED {
    base "OCICMPV4_CODE";
    description
      "DST_UNREACHABLE_ADMIN_PROHIBITED";
  }
  identity DST_UNREACHABLE_HOST_PRECEDENCE_VIOLATION {
    base "OCICMPV4_CODE";
    description
      "DST_UNREACHABLE_HOST_PRECEDENCE_VIOLATION";
  }
  identity DST_UNREACHABLE_PRECEDENCE_CUTOFF {
    base "OCICMPV4_CODE";
    description
      "DST_UNREACHABLE_PRECEDENCE_CUTOFF";
  }
  identity REDIRECT_NETWORK {
    base "OCICMPV4_CODE";
    description
      "REDIRECT_NETWORK";
  }
  identity REDIRECT_HOST {
    base "OCICMPV4_CODE";
    description
      "REDIRECT_HOST";
  }
  identity REDIRECT_TOS_NETWORK {
    base "OCICMPV4_CODE";
    description
      "REDIRECT_TOS_NETWORK";
  }
  identity REDIRECT_TOS_HOST {
    base "OCICMPV4_CODE";
    description
      "REDIRECT_TOS_HOST";
  }
  identity ECHO_NO_CODE {
    base "OCICMPV4_CODE";
    description
      "ECHO_NO_CODE";
  }
  identity ROUTER_ADVERTISEMENT_NORMAL {
    base "OCICMPV4_CODE";
    description
      "ROUTER_ADVERTISEMENT_NORMAL";
  }
  identity ROUTER_ADVERTISEMENT_DOES_NOT_ROUTE_COMMON {
    base "OCICMPV4_CODE";
    description
      "ROUTER_ADVERTISEMENT_DOES_NOT_ROUTE_COMMON";
  }
  identity ROUTER_SELECTION_NO_CODE {
    base "OCICMPV4_CODE";
    description
      "ROUTER_SELECTION_NO_CODE";
  }
  identity TIME_EXCEEDED_IN_TRANSIT {
    base "OCICMPV4_CODE";
    description
      "TIME_EXCEEDED_IN_TRANSIT";
  }
  identity TIME_EXCEEDED_FRAGMENT_REASSEMBLY_IN_TRANSIT {
    base "OCICMPV4_CODE";
    description
      "TIME_EXCEEDED_FRAGMENT_REASSEMBLY_IN_TRANSIT";
  }
  identity PARAM_PROBLEM_POINTER_INDICATES_ERR {
    base "OCICMPV4_CODE";
    description
      "PARAM_PROBLEM_POINTER_INDICATES_ERR";
  }
  identity PARAM_PROBLEM_MISSING_REQ_OPTION {
    base "OCICMPV4_CODE";
    description
      "PARAM_PROBLEM_MISSING_REQ_OPTION";
  }
  identity PARAM_PROBLEM_BAD_LENGTH {
    base "OCICMPV4_CODE";
    description
      "PARAM_PROBLEM_BAD_LENGTH";
  }
  identity TIMESTAMP_NO_CODE {
    base "OCICMPV4_CODE";
    description
      "TIMESTAMP_NO_CODE";
  }
  identity TIMESTAMP_REPLY_NO_CODE {
    base "OCICMPV4_CODE";
    description
      "TIMESTAMP_REPLY_NO_CODE";
  }
  identity PHOTURIS_BAD_SPI {
    base "OCICMPV4_CODE";
    description
      "PHOTURIS_BAD_SPI";
  }
  identity PHOTURIS_AUTH_FAILED {
    base "OCICMPV4_CODE";
    description
      "PHOTURIS_AUTH_FAILED";
  }
  identity PHOTURIS_DECOMPRESS_FAILED {
    base "OCICMPV4_CODE";
    description
      "PHOTURIS_DECOMPRESS_FAILED";
  }
  identity PHOTURIS_DECRYPTION_FAILED {
    base "OCICMPV4_CODE";
    description
      "PHOTURIS_DECRYPTION_FAILED";
  }
  identity PHOTURIS_NEED_AUTHENTICATION {
    base "OCICMPV4_CODE";
    description
      "PHOTURIS_NEED_AUTHENTICATION";
  }
  identity PHOTURIS_NEED_AUTHORIZATION {
    base "OCICMPV4_CODE";
    description
      "PHOTURIS_NEED_AUTHORIZATION";
  }
  identity EXT_ECHO_REQUEST_NO_ERROR {
    base "OCICMPV4_CODE";
    description
      "EXT_ECHO_REQUEST_NO_ERROR";
  }
  identity EXT_ECHO_REPLY_NO_ERROR {
    base "OCICMPV4_CODE";
    description
      "EXT_ECHO_REPLY_NO_ERROR";
  }
  identity EXT_ECHO_REPLY_MALFORMED_QUERY {
    base "OCICMPV4_CODE";
    description
      "EXT_ECHO_REPLY_MALFORMED_QUERY";
  }
  identity EXT_ECHO_REPLY_NO_SUCH_INTF {
    base "OCICMPV4_CODE";
    description
      "EXT_ECHO_REPLY_NO_SUCH_INTF";
  }
  identity EXT_ECHO_REPLY_NO_SUB_TABLE_ENTRY {
    base "OCICMPV4_CODE";
    description
      "EXT_ECHO_REPLY_NO_SUB_TABLE_ENTRY";
  }
  identity EXT_ECHO_REPLY_MULTIPLE_INTF_SATISFY_QUERY {
    base "OCICMPV4_CODE";
    description
      "EXT_ECHO_REPLY_MULTIPLE_INTF_SATISFY_QUERY";
  }
} // main-yang
