module arista-lanz-lanz-open-config {
  yang-version 1;
  namespace "http://arista.com/yang/experimental/eos/arista-lanz-lanz-open-config";
  prefix "arista-lanz-lanz-open-config";
  
  import openconfig-extensions { prefix "oc-ext"; }
  import arista-exp-eos { prefix "arista-exp-eos"; }
  import openconfig-interfaces { prefix "openconfig-interfaces"; }
  import openconfig-types { prefix "openconfig-types"; }
  organization
    "Arista Networks <http://arista.com/>";
  contact
    "Arista Networks <http://arista.com/>";
  description
    "Lanz Congestion Data
    
    THIS YANG MODULE WAS GENERATED FROM /src/Lanz/LanzOpenConfig.tac.
    
    DO NOT EDIT THIS FILE.";
  
  oc-ext:openconfig-version "1.0.0";
  
  revision "2025-03-17" {
    description
      "Version 1.0.0, generated on 2025-03-17";
    reference "1.0.0";
  }
  
  typedef lanz-ocentry-type {
    type enumeration {
      enum POLLING {
        value 0;
        description
          "Polling Mode";
      }
      enum CONGESTION_BEGIN {
        value 1;
        description
          "Congestion Begin";
      }
      enum CONGESTION_UPDATE {
        value 2;
        description
          "Congestion Update";
      }
      enum CONGESTION_END {
        value 3;
        description
          "Congestion End";
      }
    }
    description
      "Type of the congestion record";
  }
  
  grouping lanz-occongestion-state {
    leaf type {
      type lanz-ocentry-type;
      description
        "Entry Type";
    }
    leaf start-time {
      type openconfig-types:timeticks64;
      description
        "Start time of the congestion event";
    }
    leaf interface-id {
      type openconfig-interfaces:interface-id;
      description
        "Interface whose VOQ suffered congestion";
    }
    leaf traffic-class {
      type uint8;
      description
        "Traffic class mapped";
    }
    leaf queue-length {
      type uint32;
      description
        "Highest queue length of the VOQ during congestion";
    }
    leaf tx-latency {
      type uint32;
      units nanoseconds;
      description
        "Latency on the interface. For Entry Type 'Polling' this can be 0, which means it's N/A";
    }
    leaf duration {
      type uint64;
      units microseconds;
      description
        "Duration of congestion. On Notifying mode, duration is present only for the CONGESTION_END event. For the CONGESTION_BEGIN and CONGESTION_UPDATE events, it is 0 which corresponds to N/A";
    }
    leaf-list ingress-interfaces {
      type openconfig-interfaces:interface-id;
      description
        "Ingress port set. This includes all the interfaces for a given system core";
    }
    description
      "State of the congestion event";
  }
  
  grouping lanz-occongestion-record {
    container state {
      uses lanz-occongestion-state;
      description
        "Congestion State";
    }
    description
      "Holds the value of one Congestion event";
  }
  
  grouping lanz-oclanz {
    container congestion-record {
      uses lanz-occongestion-record;
      description
        "Most recent congestion record";
    }
    description
      "Data pertaining to Lanz";
  }
  
  augment "/arista-exp-eos:arista" {
    container lanz {
      config false;
      uses lanz-oclanz;
      description
        "lanz container";
    }
  }
} // main-yang
