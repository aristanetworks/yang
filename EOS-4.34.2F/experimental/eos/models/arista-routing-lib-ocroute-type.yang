module arista-routing-lib-ocroute-type {
  yang-version 1;
  namespace "http://arista.com/yang/experimental/eos/arista-routing-lib-ocroute-type";
  prefix "arista-routing-lib-ocroute-type";
  
  import openconfig-extensions { prefix "oc-ext"; }
  organization
    "Arista Networks <http://arista.com/>";
  contact
    "Arista Networks <http://arista.com/>";
  description
    "This is the model for OpenConfig route protocol types
    
    THIS YANG MODULE WAS GENERATED FROM /src/RoutingLib/OCRouteType.tac.
    
    DO NOT EDIT THIS FILE.";
  
  oc-ext:openconfig-version "1.0.0";
  
  revision "2025-05-06" {
    description
      "Version 1.0.0, generated on 2025-05-06";
    reference "1.0.0";
  }
  
  // covered-by: openconfig-policy-types.yang, arista-aft-augments.yang
  identity OCROUTE_TYPE {
    description
      "Internal type to represent OpenConfig protocol types";
  }
  identity BGP {
    base "OCROUTE_TYPE";
    description
      "";
  }
  identity ISIS {
    base "OCROUTE_TYPE";
    description
      "";
  }
  identity OSPF {
    base "OCROUTE_TYPE";
    description
      "";
  }
  identity OSPF3 {
    base "OCROUTE_TYPE";
    description
      "";
  }
  identity STATIC {
    base "OCROUTE_TYPE";
    description
      "";
  }
  identity DIRECTLY_CONNECTED {
    base "OCROUTE_TYPE";
    description
      "";
  }
  identity LOCAL_AGGREGATE {
    base "OCROUTE_TYPE";
    description
      "";
  }
  identity PIM {
    base "OCROUTE_TYPE";
    description
      "";
  }
  identity IGMP {
    base "OCROUTE_TYPE";
    description
      "";
  }
  identity GRIBI {
    base "OCROUTE_TYPE";
    description
      "";
  }
  identity PCEP {
    base "OCROUTE_TYPE";
    description
      "";
  }
  identity LOCAL {
    base "OCROUTE_TYPE";
    description
      "";
  }
  identity ATTACHED {
    base "OCROUTE_TYPE";
    description
      "";
  }
  identity DHCP_DEFAULT_ROUTE {
    base "OCROUTE_TYPE";
    description
      "";
  }
  identity DYNAMIC_POLICY {
    base "OCROUTE_TYPE";
    description
      "";
  }
  identity L2_NEXT_HOP_GROUP {
    base "OCROUTE_TYPE";
    description
      "";
  }
  identity STATIC_NEXT_HOP_GROUP {
    base "OCROUTE_TYPE";
    description
      "";
  }
  identity POLICY {
    base "OCROUTE_TYPE";
    description
      "";
  }
  identity RIP {
    base "OCROUTE_TYPE";
    description
      "";
  }
  identity ROUTE_CACHE_CONNECTED {
    base "OCROUTE_TYPE";
    description
      "";
  }
  identity ROUTE_CACHE_FORWARD {
    base "OCROUTE_TYPE";
    description
      "";
  }
  identity UNKNOWN {
    base "OCROUTE_TYPE";
    description
      "";
  }
  identity VCS {
    base "OCROUTE_TYPE";
    description
      "";
  }
  identity INTERNAL {
    base "OCROUTE_TYPE";
    description
      "";
  }
} // main-yang
