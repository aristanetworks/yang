module arista-acl-acl-open-config-icmpv6-types {
  yang-version 1;
  namespace "http://arista.com/yang/experimental/eos/arista-acl-acl-open-config-icmpv6-types";
  prefix "arista-acl-acl-open-config-icmpv6-types";
  
  import openconfig-extensions { prefix "oc-ext"; }
  organization
    "Arista Networks <http://arista.com/>";
  contact
    "Arista Networks <http://arista.com/>";
  description
    "Identity types relating to icmpv6
    
    THIS YANG MODULE WAS GENERATED FROM /src/Acl/AclOpenConfigIcmpv6Types.tac.
    
    DO NOT EDIT THIS FILE.";
  
  oc-ext:openconfig-version "1.0.0";
  
  revision "2024-07-19" {
    description
      "Version 1.0.0, generated on 2024-07-19";
    reference "1.0.0";
  }
  
  // covered-by: openconfig-icmpv6-types.yang
  identity OCICMPV6_TYPE {
    description
      "ocicmpv6-type";
  }
  identity DESTINATION_UNREACHABLE {
    base "OCICMPV6_TYPE";
    description
      "DESTINATION_UNREACHABLE";
  }
  identity PACKET_TOO_BIG {
    base "OCICMPV6_TYPE";
    description
      "PACKET_TOO_BIG";
  }
  identity TIME_EXCEEDED {
    base "OCICMPV6_TYPE";
    description
      "TIME_EXCEEDED_IPV6";
  }
  identity PARAMETER_PROBLEM {
    base "OCICMPV6_TYPE";
    description
      "PARAMETER_PROBLEM";
  }
  identity ECHO_REQUEST {
    base "OCICMPV6_TYPE";
    description
      "ECHO_REQUEST";
  }
  identity ECHO_REPLY {
    base "OCICMPV6_TYPE";
    description
      "ECHO_REPLY_IPV6";
  }
  identity MULTICAST_LISTENER_QUERY {
    base "OCICMPV6_TYPE";
    description
      "MULTICAST_LISTENER_QUERY";
  }
  identity MULTICAST_LISTENER_REPORT {
    base "OCICMPV6_TYPE";
    description
      "MULTICAST_LISTENER_REPORT";
  }
  identity MULTICAST_LISTENER_DONE {
    base "OCICMPV6_TYPE";
    description
      "MULTICAST_LISTENER_DONE";
  }
  identity ROUTER_SOLICITATION {
    base "OCICMPV6_TYPE";
    description
      "ROUTER_SOLICITATION_IPV6";
  }
  identity ROUTER_ADVERTISEMENT {
    base "OCICMPV6_TYPE";
    description
      "ROUTER_ADVERTISEMENT_IPV6";
  }
  identity NEIGHBOR_SOLICITATION {
    base "OCICMPV6_TYPE";
    description
      "NEIGHBOR_SOLICITATION";
  }
  identity NEIGHBOR_ADVERTISEMENT {
    base "OCICMPV6_TYPE";
    description
      "NEIGHBOR_ADVERTISEMENT";
  }
  identity REDIRECT {
    base "OCICMPV6_TYPE";
    description
      "REDIRECT_IPV6";
  }
  identity RENUNBERING {
    base "OCICMPV6_TYPE";
    description
      "RENUNBERING";
  }
  identity NODE_INFORMATION_QUERY {
    base "OCICMPV6_TYPE";
    description
      "NODE_INFORMATION_QUERY";
  }
  identity NODE_INFORMATION_RESPONSE {
    base "OCICMPV6_TYPE";
    description
      "NODE_INFORMATION_RESPONSE";
  }
  identity INVERSE_NEIGHBOR_SOLICITATION {
    base "OCICMPV6_TYPE";
    description
      "INVERSE_NEIGHBOR_SOLICITATION";
  }
  identity INVERSE_NEIGHBOR_ADVERTISEMENT {
    base "OCICMPV6_TYPE";
    description
      "INVERSE_NEIGHBOR_ADVERTISEMENT";
  }
  identity VERSION2_MULTICAST_LISTENER {
    base "OCICMPV6_TYPE";
    description
      "VERSION_2_MULTICAST_LISTENER";
  }
  identity HOME_AGENT_ADDRESS_DISCOVERY_REQUEST {
    base "OCICMPV6_TYPE";
    description
      "HOME_AGENT_ADDRESS_DISCOVERY_REQUEST";
  }
  identity HOME_AGENT_ADDRESS_DISCOVERY_REPLY {
    base "OCICMPV6_TYPE";
    description
      "HOME_AGENT_ADDRESS_DISCOVERY_REPLY";
  }
  identity MOBILE_PREFIX_SOLICITATION {
    base "OCICMPV6_TYPE";
    description
      "MOBILE_PREFIX_SOLICITATION";
  }
  identity MOBILE_PREFIX_ADVERTISEMENT {
    base "OCICMPV6_TYPE";
    description
      "MOBILE_PREFIX_ADVERTISEMENT";
  }
  identity CERTIFICATION_PATH_SOLICITATION {
    base "OCICMPV6_TYPE";
    description
      "CERTIFICATION_PATH_SOLICITATION";
  }
  identity CERTIFICATION_PATH_ADVERTISEMENT {
    base "OCICMPV6_TYPE";
    description
      "CERTIFICATION_PATH_ADVERTISEMENT";
  }
  identity MULTICAST_ROUTER_ADVERTISEMENT {
    base "OCICMPV6_TYPE";
    description
      "MULTICAST_ROUTER_ADVERTISEMENT";
  }
  identity MULTICAST_ROUTER_SOLICITATION {
    base "OCICMPV6_TYPE";
    description
      "MULTICAST_ROUTER_SOLICITATION";
  }
  identity MULTICAST_ROUTER_TERMINATION {
    base "OCICMPV6_TYPE";
    description
      "MULTICAST_ROUTER_TERMINATION";
  }
  identity FMIPV6 {
    base "OCICMPV6_TYPE";
    description
      "FMIPV6";
  }
  identity RPL_CONTROL {
    base "OCICMPV6_TYPE";
    description
      "RPL_CONTROL";
  }
  identity ILNPV6_LOCATOR_UPDATE {
    base "OCICMPV6_TYPE";
    description
      "ILNPV6_LOCATOR_UPDATE";
  }
  identity DUPLICATE_ADDRESS_REQUEST {
    base "OCICMPV6_TYPE";
    description
      "DUPLICATE_ADDRESS_REQUEST";
  }
  identity DUPLICATE_ADDRESS_CONFIRMATION {
    base "OCICMPV6_TYPE";
    description
      "DUPLICATE_ADDRESS_CONFIRMATION";
  }
  identity MPL_CONTROL {
    base "OCICMPV6_TYPE";
    description
      "MPL_CONTROL";
  }
  identity EXT_ECHO_REQUEST {
    base "OCICMPV6_TYPE";
    description
      "EXT_ECHO_REQUEST_IPV6";
  }
  identity EXT_ECHO_REPLY {
    base "OCICMPV6_TYPE";
    description
      "EXT_ECHO_REPLY_IPV6";
  }
  identity OCICMPV6_CODE {
    description
      "ocicmpv6-code";
  }
  identity DST_UNREACHABLE_NO_ROUTE_TO_DST {
    base "OCICMPV6_CODE";
    description
      "DST_UNREACHABLE_NO_ROUTE_TO_DST";
  }
  identity DST_UNREACHABLE_DST_ADMIN_PROHIBITED {
    base "OCICMPV6_CODE";
    description
      "DST_UNREACHABLE_DST_ADMIN_PROHIBITED";
  }
  identity DST_UNREACHABLE_BEYOND_SCOPE_OF_SRC {
    base "OCICMPV6_CODE";
    description
      "DST_UNREACHABLE_BEYOND_SCOPE_OF_SRC";
  }
  identity DST_UNREACHABLE_ADDR {
    base "OCICMPV6_CODE";
    description
      "DST_UNREACHABLE_ADDR";
  }
  identity DST_UNREACHABLE_PORT {
    base "OCICMPV6_CODE";
    description
      "DST_UNREACHABLE_PORT_IPV6";
  }
  identity DST_UNREACHABLE_SRC_ADDR_FAILED_POLICY {
    base "OCICMPV6_CODE";
    description
      "DST_UNREACHABLE_SRC_ADDR_FAILED_POLICY";
  }
  identity DST_UNREACHABLE_REJECT_ROUTE_TO_DST {
    base "OCICMPV6_CODE";
    description
      "DST_UNREACHABLE_REJECT_ROUTE_TO_DST";
  }
  identity DST_UNREACHABLE_ERR_IN_SRC_ROUTING_HDR {
    base "OCICMPV6_CODE";
    description
      "DST_UNREACHABLE_ERR_IN_SRC_ROUTING_HDR";
  }
  identity DST_UNREACHABLE_HDRS_TOO_LONG {
    base "OCICMPV6_CODE";
    description
      "DST_UNREACHABLE_HDRS_TOO_LONG";
  }
  identity PACKET_TOO_BIG_NO_CODE {
    base "OCICMPV6_CODE";
    description
      "PACKET_TOO_BIG_NO_CODE";
  }
  identity TIME_EXCEEDED_HOP_LIMIT {
    base "OCICMPV6_CODE";
    description
      "TIME_EXCEEDED_HOP_LIMIT";
  }
  identity TIME_EXCEEDED_FRAGMENT_REASSEMBLY {
    base "OCICMPV6_CODE";
    description
      "TIME_EXCEEDED_FRAGMENT_REASSEMBLY";
  }
  identity PARAM_PROBLEM_ERR_HDR_FIELD {
    base "OCICMPV6_CODE";
    description
      "PARAM_PROBLEM_ERR_HDR_FIELD";
  }
  identity PARAM_PROBLEM_UNRECOGNIZED_NET_HDR_TYPE {
    base "OCICMPV6_CODE";
    description
      "PARAM_PROBLEM_UNRECOGNIZED_NET_HDR_TYPE";
  }
  identity PARAM_PROBLEM_UNRECOGNIZED_IPV6_OPT {
    base "OCICMPV6_CODE";
    description
      "PARAM_PROBLEM_UNRECOGNIZED_IPV6_OPT";
  }
  identity PARAM_PROBLEM_INCOMPLETE_HDR_CHAIN {
    base "OCICMPV6_CODE";
    description
      "PARAM_PROBLEM_INCOMPLETE_HDR_CHAIN";
  }
  identity PARAM_PROBLEM_SR_UPPER_HDR_ERR {
    base "OCICMPV6_CODE";
    description
      "PARAM_PROBLEM_SR_UPPER_HDR_ERR";
  }
  identity PARAM_PROBLEM_UNRECOGNIZED_NEXT_HDR_TYPE {
    base "OCICMPV6_CODE";
    description
      "PARAM_PROBLEM_UNRECOGNIZED_NEXT_HDR_TYPE";
  }
  identity PARAM_PROBLEM_EXT_HDR_TOO_BIG {
    base "OCICMPV6_CODE";
    description
      "PARAM_PROBLEM_EXT_HDR_TOO_BIG";
  }
  identity PARAM_PROBLEM_EXT_HDR_CHAIN_TOO_LONG {
    base "OCICMPV6_CODE";
    description
      "PARAM_PROBLEM_EXT_HDR_CHAIN_TOO_LONG";
  }
  identity PARAM_PROBLEM_TOO_MANY_EXT_HDRS {
    base "OCICMPV6_CODE";
    description
      "PARAM_PROBLEM_TOO_MANY_EXT_HDRS";
  }
  identity PARAM_PROBLEM_TOO_MANY_OPTS {
    base "OCICMPV6_CODE";
    description
      "PARAM_PROBLEM_TOO_MANY_OPTS";
  }
  identity PARAM_PROBLEM_OPT_TOO_BIG {
    base "OCICMPV6_CODE";
    description
      "PARAM_PROBLEM_OPT_TOO_BIG";
  }
  identity ECHO_REQUEST_NO_CODE {
    base "OCICMPV6_CODE";
    description
      "ECHO_REQUEST_NO_CODE";
  }
  identity ECHO_REPLY_NO_CODE {
    base "OCICMPV6_CODE";
    description
      "ECHO_REPLY_NO_CODE";
  }
  identity MULTICAST_LISTENER_QUERY_NO_CODE {
    base "OCICMPV6_CODE";
    description
      "MULTICAST_LISTENER_QUERY_NO_CODE";
  }
  identity MULTICAST_LISTENER_REPORT_NO_CODE {
    base "OCICMPV6_CODE";
    description
      "MULTICAST_LISTENER_REPORT_NO_CODE";
  }
  identity MULTICAST_LISTENER_DONE_NO_CODE {
    base "OCICMPV6_CODE";
    description
      "MULTICAST_LISTENER_DONE_NO_CODE";
  }
  identity ROUTER_SOLICITATION_NO_CODE {
    base "OCICMPV6_CODE";
    description
      "ROUTER_SOLICITATION_NO_CODE";
  }
  identity ROUTER_ADVERTISEMENT_NO_CODE {
    base "OCICMPV6_CODE";
    description
      "ROUTER_ADVERTISEMENT_NO_CODE";
  }
  identity NEIGHBOR_SOLICITATION_NO_CODE {
    base "OCICMPV6_CODE";
    description
      "NEIGHBOR_SOLICITATION_NO_CODE";
  }
  identity NEIGHBOR_ADVERTISEMENT_NO_CODE {
    base "OCICMPV6_CODE";
    description
      "NEIGHBOR_ADVERTISEMENT_NO_CODE";
  }
  identity REDIRECT_NO_CODE {
    base "OCICMPV6_CODE";
    description
      "REDIRECT_NO_CODE";
  }
  identity RENUMBERING_COMMAND {
    base "OCICMPV6_CODE";
    description
      "RENUMBERING_COMMAND";
  }
  identity RENUNBERING_RESULT {
    base "OCICMPV6_CODE";
    description
      "RENUNBERING_RESULT";
  }
  identity RENUNBERING_SEQ_NUM_RESET {
    base "OCICMPV6_CODE";
    description
      "RENUNBERING_SEQ_NUM_RESET";
  }
  identity NODE_INFORMATION_QUERY_IPV6_ADDR {
    base "OCICMPV6_CODE";
    description
      "NODE_INFORMATION_QUERY_IPV6_ADDR";
  }
  identity NODE_INFORMATION_QUERY_NAME {
    base "OCICMPV6_CODE";
    description
      "NODE_INFORMATION_QUERY_NAME";
  }
  identity NODE_INFORMATION_QUERY_IPV4_ADDR {
    base "OCICMPV6_CODE";
    description
      "NODE_INFORMATION_QUERY_IPV4_ADDR";
  }
  identity NODE_INFORMATION_RESPONSE_SUCCESS {
    base "OCICMPV6_CODE";
    description
      "NODE_INFORMATION_RESPONSE_SUCCESS";
  }
  identity NODE_INFORMATION_RESPONSE_REFUSED {
    base "OCICMPV6_CODE";
    description
      "NODE_INFORMATION_RESPONSE_REFUSED";
  }
  identity NODE_INFORMATION_RESPONSE_UNKNOWN {
    base "OCICMPV6_CODE";
    description
      "NODE_INFORMATION_RESPONSE_UNKNOWN";
  }
  identity INVERSE_NEIGHBOR_SOLICITATION_NO_CODE {
    base "OCICMPV6_CODE";
    description
      "INVERSE_NEIGHBOR_SOLICITATION_NO_CODE";
  }
  identity INVERSE_NEIGHBOR_ADVERTISEMENT_NO_CODE {
    base "OCICMPV6_CODE";
    description
      "INVERSE_NEIGHBOR_ADVERTISEMENT_NO_CODE";
  }
  identity HOME_AGENT_ADDRESS_DISCOVERY_REQUEST_NO_CODE {
    base "OCICMPV6_CODE";
    description
      "HOME_AGENT_ADDRESS_DISCOVERY_REQUEST_NO_CODE";
  }
  identity HOME_AGENT_ADDRESS_DISCOVERY_REPLY_NO_CODE {
    base "OCICMPV6_CODE";
    description
      "HOME_AGENT_ADDRESS_DISCOVERY_REPLY_NO_CODE";
  }
  identity MOBILE_PREFIX_SOLICITATION_NO_CODE {
    base "OCICMPV6_CODE";
    description
      "MOBILE_PREFIX_SOLICITATION_NO_CODE";
  }
  identity MOBILE_PREFIX_ADVERTISEMENT_NO_CODE {
    base "OCICMPV6_CODE";
    description
      "MOBILE_PREFIX_ADVERTISEMENT_NO_CODE";
  }
  identity DUPLICATE_ADDRESS_REQUEST_DAR {
    base "OCICMPV6_CODE";
    description
      "DUPLICATE_ADDRESS_REQUEST_DAR";
  }
  identity DUPLICATE_ADDRESS_REQUEST_EDAR_ROVR64 {
    base "OCICMPV6_CODE";
    description
      "DUPLICATE_ADDRESS_REQUEST_EDAR_ROVR_64";
  }
  identity DUPLICATE_ADDRESS_REQUEST_EDAR_ROVR128 {
    base "OCICMPV6_CODE";
    description
      "DUPLICATE_ADDRESS_REQUEST_EDAR_ROVR_128";
  }
  identity DUPLICATE_ADDRESS_REQUEST_EDAR_ROVR192 {
    base "OCICMPV6_CODE";
    description
      "DUPLICATE_ADDRESS_REQUEST_EDAR_ROVR_192";
  }
  identity DUPLICATE_ADDRESS_REQUEST_EDAR_ROVR256 {
    base "OCICMPV6_CODE";
    description
      "DUPLICATE_ADDRESS_REQUEST_EDAR_ROVR_256";
  }
  identity DUPLICATE_ADDRESS_REPLY_DAC {
    base "OCICMPV6_CODE";
    description
      "DUPLICATE_ADDRESS_REPLY_DAC";
  }
  identity DUPLICATE_ADDRESS_REPLY_EDAC_ROVR64 {
    base "OCICMPV6_CODE";
    description
      "DUPLICATE_ADDRESS_REPLY_EDAC_ROVR_64";
  }
  identity DUPLICATE_ADDRESS_REPLY_EDAC_ROVR128 {
    base "OCICMPV6_CODE";
    description
      "DUPLICATE_ADDRESS_REPLY_EDAC_ROVR_128";
  }
  identity DUPLICATE_ADDRESS_REPLY_EDAC_ROVR192 {
    base "OCICMPV6_CODE";
    description
      "DUPLICATE_ADDRESS_REPLY_EDAC_ROVR_192";
  }
  identity DUPLICATE_ADDRESS_REPLY_EDAC_ROVR256 {
    base "OCICMPV6_CODE";
    description
      "DUPLICATE_ADDRESS_REPLY_EDAC_ROVR_256";
  }
  identity EXT_ECHO_REQUEST_NO_ERROR {
    base "OCICMPV6_CODE";
    description
      "EXT_ECHO_REQUEST_NO_ERROR_IPV6";
  }
  identity EXT_ECHO_REPLY_NO_ERROR {
    base "OCICMPV6_CODE";
    description
      "EXT_ECHO_REPLY_NO_ERROR_IPV6";
  }
  identity EXT_ECHO_REPLY_MALFORMED_QUERY {
    base "OCICMPV6_CODE";
    description
      "EXT_ECHO_REPLY_MALFORMED_QUERY_IPV6";
  }
  identity EXT_ECHO_REPLY_NO_SUCH_INTERFACE {
    base "OCICMPV6_CODE";
    description
      "EXT_ECHO_REPLY_NO_SUCH_INTERFACE";
  }
  identity EXT_ECHO_REPLY_NO_SUCH_TABLE_ENTRY {
    base "OCICMPV6_CODE";
    description
      "EXT_ECHO_REPLY_NO_SUCH_TABLE_ENTRY";
  }
  identity EXT_ECHO_REPLY_MULTIPLE_INTF_SATISFY_QUERY {
    base "OCICMPV6_CODE";
    description
      "EXT_ECHO_REPLY_MULTIPLE_INTF_SATISFY_QUERY_IPV6";
  }
} // main-yang
