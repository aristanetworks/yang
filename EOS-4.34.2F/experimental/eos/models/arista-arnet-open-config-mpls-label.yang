module arista-arnet-open-config-mpls-label {
  yang-version 1;
  namespace "http://arista.com/yang/experimental/eos/arista-arnet-open-config-mpls-label";
  prefix "arista-arnet-open-config-mpls-label";
  
  import openconfig-extensions { prefix "oc-ext"; }
  organization
    "Arista Networks <http://arista.com/>";
  contact
    "Arista Networks <http://arista.com/>";
  description
    "MPLS label
    
    THIS YANG MODULE WAS GENERATED FROM /src/Arnet/OpenConfigMplsLabel.tac.
    
    DO NOT EDIT THIS FILE.";
  
  oc-ext:openconfig-version "4.0.0";
  
  revision "2024-01-05" {
    description
      "Version 4.0.0, generated on 2024-01-05";
    reference "4.0.0";
  }
  
  // covered-by: openconfig-mpls-types.yang
  typedef arnet-open-config-mpls-label-num {
    type uint32 {
      range "16..1048575";
    }
    default 16;
    description
      "MPLS label (unreserved values)";
  }
  
  typedef arnet-open-config-mpls-label-enum {
    type enumeration {
      enum NO_LABEL {
        value 0;
        description
          "no label assigned";
      }
      enum IPV4_EXPLICIT_NULL {
        value 1;
        description
          "IPv4 explicit null";
      }
      enum ROUTER_ALERT {
        value 2;
        description
          "router alert";
      }
      enum IPV6_EXPLICIT_NULL {
        value 3;
        description
          "IPv6 explicit null";
      }
      enum IMPLICIT_NULL {
        value 4;
        description
          "implicit null";
      }
      enum ENTROPY_LABEL_INDICATOR {
        value 5;
        description
          "entropy label indicator";
      }
    }
    description
      "MPLS label";
  }
  
} // main-yang
