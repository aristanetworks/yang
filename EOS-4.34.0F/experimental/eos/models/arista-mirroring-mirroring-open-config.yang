module arista-mirroring-mirroring-open-config {
  yang-version 1;
  namespace "http://arista.com/yang/experimental/eos/arista-mirroring-mirroring-open-config";
  prefix "arista-mirroring-mirroring-open-config";

  import openconfig-extensions { prefix "oc-ext"; }
  import arista-exp-eos { prefix "arista-exp-eos"; }
  import arista-mirroring-tap-agg-common { prefix "arista-mirroring-tap-agg-common"; }
  import openconfig-interfaces { prefix "openconfig-interfaces"; }
  organization
    "Arista Networks <http://arista.com/>";
  contact
    "Arista Networks <http://arista.com/>";
  description
    "OpenConfig support for Tap Aggregation Config

    THIS YANG MODULE WAS GENERATED FROM /src/Mirroring/MirroringOpenConfig.tac.

    DO NOT EDIT THIS FILE.";

  oc-ext:openconfig-version "1.0.0";

  revision "2024-08-12" {
    description
      "Version 1.0.0, generated on 2024-08-12";
    reference "1.0.0";
  }

  grouping mirroring-open-config-ocno-err-disabled-intf-name {
    leaf name {
      type openconfig-interfaces:interface-id;
      description
        "name";
    }
    description
      "NoErrDisabled interface name";
  }

  grouping mirroring-open-config-ocno-err-disabled-intf-config {
    leaf name {
      type openconfig-interfaces:interface-id;
      description
        "name";
    }
    container config {
      uses mirroring-open-config-ocno-err-disabled-intf-name;
      description
        "config";
    }
    container state {
      uses mirroring-open-config-ocno-err-disabled-intf-name;
      config false;
      description
        "state";
    }
    description
      "NoErrDisable interface config";
  }

  grouping mirroring-open-config-octap-agg-no-err-disable-intfs-config {
    list interface {
      key "name";
      uses mirroring-open-config-ocno-err-disabled-intf-config;
      description
        "interface";
    }
    leaf name {
      type string;
      description
        "name of the grouping";
    }
    description
      "Configure Tap Aggregation noErrDisable interfaces";
  }

  grouping mirroring-open-config-octap-agg-mode-config {
    leaf mode {
      type arista-mirroring-tap-agg-common:tap-agg-tap-agg-mode;
      description
        "mode";
    }
    leaf tcam-profile {
      type string;
      description
        "tcam-profile";
    }
    description
      "Configure Tap Aggregation mode and tcamProfile";
  }

  augment "/arista-exp-eos:arista/arista-mirroring-tap-agg-common:tap-aggregation" {
    container noerrdisable {
      container interfaces {
        list interface {
          key "name";
     uses mirroring-open-config-ocno-err-disabled-intf-config;
     description
         "interface list";
      }
       description
         "interfaces container";
      }
       description
         "noerrdisable container";
      }
      container config {
     uses mirroring-open-config-octap-agg-mode-config;
     description
         "config container";
      }
  }
} // main-yang
