module arista-ale-counters-open-config-specialized-counters {
  yang-version 1;
  namespace "http://arista.com/yang/experimental/eos/arista-ale-counters-open-config-specialized-counters";
  prefix "arista-ale-counters-open-config-specialized-counters";

  import openconfig-extensions { prefix "oc-ext"; }
  import openconfig-platform { prefix "openconfig-platform"; }
  organization
    "Arista Networks <http://arista.com/>";
  contact
    "Arista Networks <http://arista.com/>";
  description
    "Specialized counters

    THIS YANG MODULE WAS GENERATED FROM /src/AleCounters/OpenConfigSpecializedCounters.tac.

    DO NOT EDIT THIS FILE.";

  oc-ext:openconfig-version "1.0.0";

  revision "2021-10-20" {
    description
      "Version 1.0.0, generated on 2021-10-20";
    reference "1.0.0";
  }

  grouping ale-counters-open-config-specialized-sand-counters {
    leaf total-specialized-counters {
      type uint64;
      description
        "Sample specialized counter.";
    }
    description
      "Container for Sand specific specialized counters.";
  }

  grouping ale-counters-open-config-specialized-counters {
    container sand {
      uses ale-counters-open-config-specialized-sand-counters;
      description
        "Container for Sand specific specialized counters.";
    }
    leaf name {
      type string;
      description
        "name of the grouping";
    }
    description
      "";
  }

  grouping ale-counters-open-config-specialized {
    list specialized-counters {
      key "name";
      uses ale-counters-open-config-specialized-counters;
      description
        "";
    }
    leaf name {
      type string;
      description
        "name of the grouping";
    }
    description
      "";
  }

  augment "/openconfig-platform:components/openconfig-platform:component/openconfig-platform:integrated-circuit" {
    container specialized-counters {
      container vendor {
        container arista {
          config false;
     uses ale-counters-open-config-specialized-counters;
     description
         "arista container";
      }
       description
         "vendor container";
      }
       description
         "specialized-counters container";
      }
  }
} // main-yang
