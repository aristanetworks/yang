module arista-mirroring-tap-agg-common {
  yang-version 1;
  namespace "http://arista.com/yang/experimental/eos/arista-mirroring-tap-agg-common";
  prefix "arista-mirroring-tap-agg-common";

  import openconfig-extensions { prefix "oc-ext"; }
  import arista-exp-eos { prefix "arista-exp-eos"; }
  organization
    "Arista Networks <http://arista.com/>";
  contact
    "Arista Networks <http://arista.com/>";
  description
    "OpenConfig Model for Tap Aggregation State

    THIS YANG MODULE WAS GENERATED FROM /src/Mirroring/TapAggCommon.tac.

    DO NOT EDIT THIS FILE.";

  oc-ext:openconfig-version "1.0.0";

  revision "2024-08-12" {
    description
      "Version 1.0.0, generated on 2024-08-12";
    reference "1.0.0";
  }

  typedef tap-agg-tap-agg-mode {
    type enumeration {
      enum MODE_NONE {
        value 0;
        description
          "TAP_AGG_MODE_NONE";
      }
      enum MODE_EXCLUSIVE {
        value 1;
        description
          "TAP_AGG_MODE_EXCLUSIVE";
      }
    }
    description
      "Tap Aggregation modes";
  }

  grouping tap-agg-cli-config {
    leaf mode {
      type tap-agg-tap-agg-mode;
      description
        "mode";
    }
    leaf tcam-profile {
      type string;
      description
        "tcam-profile";
    }
    description
      "Tap Aggregation configuration status";
  }

  augment "/arista-exp-eos:arista" {
    container tap-aggregation {
      container state {
        config false;
     uses tap-agg-cli-config;
     description
         "state container";
      }
       description
         "tap-aggregation container";
      }
  }
} // main-yang
