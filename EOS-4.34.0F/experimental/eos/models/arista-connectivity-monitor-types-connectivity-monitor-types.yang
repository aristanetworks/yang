module arista-connectivity-monitor-types-connectivity-monitor-types {
  yang-version 1;
  namespace "http://arista.com/yang/experimental/eos/arista-connectivity-monitor-types-connectivity-monitor-types";
  prefix "arista-connectivity-monitor-types-connectivity-monitor-types";

  import openconfig-extensions { prefix "oc-ext"; }
  import arista-arnet-vrf-name { prefix "arista-arnet-vrf-name"; }
  import arista-eos-types { prefix "arista-eos-types"; }
  import arista-exp-eos { prefix "arista-exp-eos"; }
  import openconfig-inet-types { prefix "openconfig-inet-types"; }
  organization
    "Arista Networks <http://arista.com/>";
  contact
    "Arista Networks <http://arista.com/>";
  description
    "Yang model for ConnectivityMonitor

    THIS YANG MODULE WAS GENERATED FROM /src/ConnectivityMonitorTypes/ConnectivityMonitorTypes.tac.

    DO NOT EDIT THIS FILE.";

  oc-ext:openconfig-version "1.0.0";

  revision "2024-05-02" {
    description
      "Version 1.0.0, generated on 2024-05-02";
    reference "1.0.0";
  }

  grouping connectivity-monitor-host-name-vrf-key {
    leaf host-name {
      type string;
      description
        "Name of the host";
    }
    leaf vrf-name {
      type arista-arnet-vrf-name:l3-vrf-name;
      description
        "Name of the vrf";
    }
    description
      "Container key for host name vrf";
  }

  grouping connectivity-monitor-icmp-stats-key {
    leaf interface-name {
      type string;
      description
        "Source interface used by this particular probe";
    }
    leaf ip-addr {
      type openconfig-inet-types:ip-address;
      description
        "IP address of the endpoint being probed";
    }
    description
      "Container key for ICMP statistics";
  }

  grouping connectivity-monitor-http-stats-key {
    leaf interface-name {
      type string;
      description
        "Source interface used by this particular probe";
    }
    leaf url {
      type string;
      description
        "URL endpoint being probed via HTTP for this probe";
    }
    description
      "Container key for HTTP statistics";
  }

  grouping connectivity-monitor-tcp-stats-key {
    leaf interface-name {
      type string;
      description
        "Source interface used by this particular probe";
    }
    leaf ip-addr {
      type openconfig-inet-types:ip-address;
      description
        "IP address of the endpoint being probed";
    }
    leaf dport {
      type uint16;
      description
        "Server port number for TCP probe";
    }
    description
      "Container key for TCP statistics";
  }

  grouping connectivity-monitor-icmp-stats {
    uses connectivity-monitor-icmp-stats-key;
    leaf latency {
      type binary {
         length 8;
      }
      description
        "Latency value in milliseconds for ICMP probe";
    }
    leaf jitter {
      type binary {
         length 8;
      }
      description
        "Jitter value in milliseconds for ICMP probe";
    }
    leaf packet-loss {
      type uint8;
      description
        "Number of data packets that fail to arrive
                             at their destination for ICMP probe";
    }
    leaf icmp-probe-error {
      type string;
      description
        "Represents the ICMP probe errors such as
                             Destination Unreachable, Time Exceeded,
                             Source Quench etc.";
    }
    description
      "Container for ICMP statistics";
  }

  grouping connectivity-monitor-http-stats {
    uses connectivity-monitor-http-stats-key;
    leaf http-response-time {
      type binary {
         length 8;
      }
      description
        "Time measured in milliseconds that it takes for a server
                             to respond to a request";
    }
    leaf http-probe-error {
      type string;
      description
        "Represents the HTTP probe errors such as
                             Bad Gateway, Malformed Request etc.";
    }
    description
      "Container for HTTP statistics";
  }

  grouping connectivity-monitor-tcp-stats {
    uses connectivity-monitor-tcp-stats-key;
    leaf latency {
      type binary {
         length 8;
      }
      description
        "Latency value in milliseconds for TCP probe";
    }
    description
      "Container for TCP statistics";
  }

  grouping connectivity-monitor-reachability-stats {
    leaf interface-name {
      type string;
      description
        "Source interface";
    }
    leaf sequential-failed-probe-count-icmp {
      type uint32;
      description
        "Number of sequential ICMP probes
                             that did not receive any response";
    }
    leaf sequential-failed-probe-count-http {
      type uint32;
      description
        "Number of sequential HTTP probes
                             that did not receive any response";
    }
    leaf host-unreachable {
      type boolean;
      description
        "Host is unreachable if the sequential lost probe count
                             crosses the threshold. It is true if both ICMP and HTTP
                             probes are unreachable";
    }
    leaf host-unreachable-icmp {
      type boolean;
      description
        "Returns True if ICMP is unreachable";
    }
    leaf host-unreachable-http {
      type boolean;
      description
        "Returns True if HTTP is unreachable";
    }
    leaf last-response-at-icmp {
      type arista-eos-types:seconds;
      description
        "Timestamp in seconds when the last ICMP
                             response was received";
    }
    leaf last-response-at-http {
      type arista-eos-types:seconds;
      description
        "Timestamp in seconds when the last HTTP
                             response was received";
    }
    description
      "Container for reachability statistics";
  }

  grouping connectivity-monitor-host-status {
    uses connectivity-monitor-host-name-vrf-key;
    list icmp-stats {
      key "interface-name ip-addr";
      uses connectivity-monitor-icmp-stats;
      description
        "Holds the ICMP stats for each IP and interface combination
                                 probed via this host";
    }
    list http-stats {
      key "interface-name url";
      uses connectivity-monitor-http-stats;
      description
        "Holds the HTTP stats for each URL and interface combination
                                 probed via this host";
    }
    list tcp-stats {
      key "interface-name ip-addr dport";
      uses connectivity-monitor-tcp-stats;
      description
        "Holds the TCP stats for each IP:port and interface
                                 combination probed via this host";
    }
    list reachability-stats {
      key "interface-name";
      uses connectivity-monitor-reachability-stats;
      description
        "A collection per interface that stores the
                                 information of the probe reachability statistics";
    }
    description
      "Container for host status which is a collection of
                        ICMP and HTTP probe statistics";
  }

  grouping connectivity-monitor-status-dir {
    list host-status {
      key "host-name vrf-name";
      uses connectivity-monitor-host-status;
      description
        "Host status containing probe statistics
                                 keyed by hostname and VRF name";
    }
    leaf name {
      type string;
      description
        "name of the grouping";
    }
    description
      "Enclosing container for connectivity monitor status";
  }

  augment "/arista-exp-eos:arista" {
    container connectivity-monitor {
      container clients {
        list client {
          key "name";
          config false;
     uses connectivity-monitor-status-dir;
     description
         "client list";
      }
       description
         "clients container";
      }
       description
         "connectivity-monitor container";
      }
  }
} // main-yang
