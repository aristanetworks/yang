module arista-intf-intf {
  yang-version 1;
  namespace "http://arista.com/yang/experimental/eos/arista-intf-intf";
  prefix "arista-intf-intf";

  import openconfig-extensions { prefix "oc-ext"; }
  import arista-arnet-rate { prefix "arista-arnet-rate"; }
  organization
    "Arista Networks <http://arista.com/>";
  contact
    "Arista Networks <http://arista.com/>";
  description
    "Defines interface rates

    THIS YANG MODULE WAS GENERATED FROM /src/Intf/Intf.tac.

    DO NOT EDIT THIS FILE.";

  oc-ext:openconfig-version "0.1.0";

  revision "2023-08-15" {
    description
      "Version 0.1.0, generated on 2023-08-15";
    reference "0.1.0";
  }

  grouping interface-intf-rates {
    leaf out-pkts-rate {
      type arista-arnet-rate:arnet-packets-per-second;
      description
        "";
    }
    leaf in-pkts-rate {
      type arista-arnet-rate:arnet-packets-per-second;
      description
        "";
    }
    leaf out-bits-rate {
      type arista-arnet-rate:arnet-bits-per-second;
      description
        "";
    }
    leaf in-bits-rate {
      type arista-arnet-rate:arnet-bits-per-second;
      description
        "";
    }
    description
      "";
  }

} // main-yang
