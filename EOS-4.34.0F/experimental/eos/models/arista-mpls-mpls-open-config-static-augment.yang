module arista-mpls-mpls-open-config-static-augment {
  yang-version 1;
  namespace "http://arista.com/yang/experimental/eos/arista-mpls-mpls-open-config-static-augment";
  prefix "arista-mpls-mpls-open-config-static-augment";

  import openconfig-extensions { prefix "oc-ext"; }
  import openconfig-inet-types { prefix "openconfig-inet-types"; }
  import openconfig-mpls-types { prefix "openconfig-mpls-types"; }
  import openconfig-network-instance { prefix "openconfig-network-instance"; }
  organization
    "Arista Networks <http://arista.com/>";
  contact
    "Arista Networks <http://arista.com/>";
  description
    "model for MPLS static LSPs

    THIS YANG MODULE WAS GENERATED FROM /src/Mpls/MplsOpenConfigStatic.tac.

    DO NOT EDIT THIS FILE.";

  oc-ext:openconfig-version "3.4.0";

  revision "2024-03-11" {
    description
      "Version 3.4.0, generated on 2024-03-11";
    reference "3.4.0";
  }

  identity PAYLOAD_TYPE {
    description
      "base identity for supported MPLS payload types";
  }
  identity PAYLOAD_MPLS {
    base "PAYLOAD_TYPE";
    description
      "Specifies underlying payload type as MPLS label i.e, represents stacked MPLS labels";
  }
  identity PAYLOAD_IPV4 {
    base "PAYLOAD_TYPE";
    description
      "Specifies underlying payload type as IPV4";
  }
  identity PAYLOAD_IPV6 {
    base "PAYLOAD_TYPE";
    description
      "Specifies underlying payload type as IPV6";
  }
  grouping mpls-ocmpls-static-lsp-key {
    description
      "";
  }

  grouping mpls-ocmpls-static-lsp-next-hop-config-base {
    description
      "";
  }

  grouping mpls-ocmpls-static-lsp-transit-next-hop-config {
    uses mpls-ocmpls-static-lsp-next-hop-config-base;
    description
      "";
  }

  grouping mpls-ocmpls-static-lsp-egress-next-hop-config {
    leaf payload-type {
      type identityref {
         base "PAYLOAD_TYPE";
      }
      description
        "Underlying payload type of the MPLS packet";
    }
    leaf access-list-bypass {
      type boolean;
      description
        "Skip access-list if set to true";
    }
    uses mpls-ocmpls-static-lsp-next-hop-config-base;
    description
      "";
  }

  augment "/openconfig-network-instance:network-instances/openconfig-network-instance:network-instance/openconfig-network-instance:mpls/openconfig-network-instance:lsps/openconfig-network-instance:static-lsps/openconfig-network-instance:static-lsp/openconfig-network-instance:egress/openconfig-network-instance:lsp-next-hops/openconfig-network-instance:lsp-next-hop/openconfig-network-instance:config" {
    leaf payload-type {
      type identityref {
         base "PAYLOAD_TYPE";
      }
      description
        "Underlying payload type of the MPLS packet";
    }
    leaf access-list-bypass {
      type boolean;
      description
        "Skip access-list if set to true";
    }
    description
      "";
  }
  augment "/openconfig-network-instance:network-instances/openconfig-network-instance:network-instance/openconfig-network-instance:mpls/openconfig-network-instance:lsps/openconfig-network-instance:static-lsps/openconfig-network-instance:static-lsp/openconfig-network-instance:egress/openconfig-network-instance:lsp-next-hops/openconfig-network-instance:lsp-next-hop/openconfig-network-instance:state" {
    leaf payload-type {
      type identityref {
         base "PAYLOAD_TYPE";
      }
      description
        "Underlying payload type of the MPLS packet";
    }
    leaf access-list-bypass {
      type boolean;
      description
        "Skip access-list if set to true";
    }
    description
      "";
  }
  grouping mpls-ocmpls-static-lsp-egress-next-hop {
    description
      "";
  }

  grouping mpls-ocmpls-static-lsp-egress-next-hops {
    description
      "";
  }

  grouping mpls-ocmpls-static-lsp-transit-next-hop {
    description
      "";
  }

  grouping mpls-ocmpls-static-lsp-transit-next-hops {
    description
      "";
  }

  grouping mpls-ocmpls-static-lsp-config {
    description
      "";
  }

  grouping mpls-ocmpls-static-lsp-transit {
    description
      "";
  }

  grouping mpls-ocmpls-static-lsp-egress {
    description
      "";
  }

  grouping mpls-ocmpls-static-lsp {
    description
      "";
  }

  grouping mpls-ocmpls-static-lsp-dir {
    description
      "Mpls model for Mpls static lsp";
  }

} // augmented-yang
