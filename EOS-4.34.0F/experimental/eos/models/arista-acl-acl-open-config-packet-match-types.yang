module arista-acl-acl-open-config-packet-match-types {
  yang-version 1;
  namespace "http://arista.com/yang/experimental/eos/arista-acl-acl-open-config-packet-match-types";
  prefix "arista-acl-acl-open-config-packet-match-types";

  import openconfig-extensions { prefix "oc-ext"; }
  organization
    "Arista Networks <http://arista.com/>";
  contact
    "Arista Networks <http://arista.com/>";
  description
    "External tac model for traffic policy

    THIS YANG MODULE WAS GENERATED FROM /src/Acl/AclOpenConfigPacketMatchTypes.tac.

    DO NOT EDIT THIS FILE.";

  oc-ext:openconfig-version "1.0.0";

  revision "2024-08-19" {
    description
      "Version 1.0.0, generated on 2024-08-19";
    reference "1.0.0";
  }

  // covered-by: openconfig-packet-match-types.yang, openconfig-acl.yang
  typedef acl-open-config-ethertype-num {
    type uint16;
    description
      "acl-open-config-ethertype-num";
  }

  identity ACL_OPEN_CONFIG_ETHERTYPE {
    description
      "acl-open-config-ethertype";
  }
  identity ETHERTYPE_IPV4 {
    base "ACL_OPEN_CONFIG_ETHERTYPE";
    description
      "ETHERTYPE_IPV4";
  }
  identity ETHERTYPE_ARP {
    base "ACL_OPEN_CONFIG_ETHERTYPE";
    description
      "ETHERTYPE_ARP";
  }
  identity ETHERTYPE_VLAN {
    base "ACL_OPEN_CONFIG_ETHERTYPE";
    description
      "ETHERTYPE_VLAN";
  }
  identity ETHERTYPE_IPV6 {
    base "ACL_OPEN_CONFIG_ETHERTYPE";
    description
      "ETHERTYPE_IPV6";
  }
  identity ETHERTYPE_MPLS {
    base "ACL_OPEN_CONFIG_ETHERTYPE";
    description
      "ETHERTYPE_MPLS";
  }
  identity ETHERTYPE_LLDP {
    base "ACL_OPEN_CONFIG_ETHERTYPE";
    description
      "ETHERTYPE_LLDP";
  }
  identity ETHERTYPE_ROCE {
    base "ACL_OPEN_CONFIG_ETHERTYPE";
    description
      "ETHERTYPE_ROCE";
  }
  identity ACL_OPEN_CONFIG_IP_PROTOCOL {
    description
      "acl-open-config-ip-protocol";
  }
  identity IP_TCP {
    base "ACL_OPEN_CONFIG_IP_PROTOCOL";
    description
      "IP_TCP";
  }
  identity IP_UDP {
    base "ACL_OPEN_CONFIG_IP_PROTOCOL";
    description
      "IP_UDP";
  }
  identity IP_ICMP {
    base "ACL_OPEN_CONFIG_IP_PROTOCOL";
    description
      "IP_ICMP";
  }
  identity IP_IGMP {
    base "ACL_OPEN_CONFIG_IP_PROTOCOL";
    description
      "IP_IGMP";
  }
  identity IP_PIM {
    base "ACL_OPEN_CONFIG_IP_PROTOCOL";
    description
      "IP_PIM";
  }
  identity IP_RSVP {
    base "ACL_OPEN_CONFIG_IP_PROTOCOL";
    description
      "IP_RSVP";
  }
  identity IP_GRE {
    base "ACL_OPEN_CONFIG_IP_PROTOCOL";
    description
      "IP_GRE";
  }
  identity IP_AUTH {
    base "ACL_OPEN_CONFIG_IP_PROTOCOL";
    description
      "IP_AUTH";
  }
  identity IP_L_2_TP {
    base "ACL_OPEN_CONFIG_IP_PROTOCOL";
    description
      "IP_L_2_TP";
  }
  identity IP_IN_IP {
    base "ACL_OPEN_CONFIG_IP_PROTOCOL";
    description
      "IP_IN_IP";
  }
  identity ACL_OPEN_CONFIG_ACL_TYPE {
    description
      "acl-open-config-acl-type";
  }
  identity ACL_IPV4 {
    base "ACL_OPEN_CONFIG_ACL_TYPE";
    description
      "ACL_IPV4";
  }
  identity ACL_IPV6 {
    base "ACL_OPEN_CONFIG_ACL_TYPE";
    description
      "ACL_IPV6";
  }
  identity ACL_L2 {
    base "ACL_OPEN_CONFIG_ACL_TYPE";
    description
      "ACL_L_2";
  }
  identity ACL_MIXED {
    base "ACL_OPEN_CONFIG_ACL_TYPE";
    description
      "ACL_MIXED";
  }
  identity ACL_MPLS {
    base "ACL_OPEN_CONFIG_ACL_TYPE";
    description
      "ACL_MPLS";
  }
  identity ACL_OPEN_CONFIG_TCP_FLAGS {
    description
      "acl-open-config-tcp-flags";
  }
  identity TCP_FIN {
    base "ACL_OPEN_CONFIG_TCP_FLAGS";
    description
      "TCP_FIN";
  }
  identity TCP_SYN {
    base "ACL_OPEN_CONFIG_TCP_FLAGS";
    description
      "TCP_SYN";
  }
  identity TCP_RST {
    base "ACL_OPEN_CONFIG_TCP_FLAGS";
    description
      "TCP_RST";
  }
  identity TCP_PSH {
    base "ACL_OPEN_CONFIG_TCP_FLAGS";
    description
      "TCP_PSH";
  }
  identity TCP_ACK {
    base "ACL_OPEN_CONFIG_TCP_FLAGS";
    description
      "TCP_ACK";
  }
  identity TCP_URG {
    base "ACL_OPEN_CONFIG_TCP_FLAGS";
    description
      "TCP_URG";
  }
  identity TCP_ECE {
    base "ACL_OPEN_CONFIG_TCP_FLAGS";
    description
      "TCP_ECE";
  }
  identity TCP_CWR {
    base "ACL_OPEN_CONFIG_TCP_FLAGS";
    description
      "TCP_CWR";
  }
  identity ACL_OPEN_CONFIG_ACL_COUNTER_CAPABILITY {
    description
      "acl-open-config-acl-counter-capability";
  }
  identity INTERFACE_ONLY {
    base "ACL_OPEN_CONFIG_ACL_COUNTER_CAPABILITY";
    description
      "INTERFACE_ONLY";
  }
  identity AGGREGATE_ONLY {
    base "ACL_OPEN_CONFIG_ACL_COUNTER_CAPABILITY";
    description
      "AGGREGATE_ONLY";
  }
  identity INTERFACE_AGGREGATE {
    base "ACL_OPEN_CONFIG_ACL_COUNTER_CAPABILITY";
    description
      "INTERFACE_AGGREGATE";
  }
  identity ACL_OPEN_CONFIG_FORWARDING_ACTION {
    description
      "acl-open-config-forwarding-action";
  }
  identity ACCEPT {
    base "ACL_OPEN_CONFIG_FORWARDING_ACTION";
    description
      "ACCEPT";
  }
  identity DROP {
    base "ACL_OPEN_CONFIG_FORWARDING_ACTION";
    description
      "DROP";
  }
  identity REJECT {
    base "ACL_OPEN_CONFIG_FORWARDING_ACTION";
    description
      "REJECT";
  }
  identity ACL_OPEN_CONFIG_LOG_ACTION {
    description
      "acl-open-config-log-action";
  }
  identity LOG_NONE {
    base "ACL_OPEN_CONFIG_LOG_ACTION";
    description
      "LOG_NONE";
  }
  identity LOG_SYSLOG {
    base "ACL_OPEN_CONFIG_LOG_ACTION";
    description
      "LOG_SYSLOG";
  }
  typedef acl-open-config-explicit-detail-mode {
    type enumeration {
      enum ANY {
        value 0;
        description
          "ANY";
      }
      enum ALL {
        value 1;
        description
          "ALL";
      }
    }
    description
      "acl-open-config-explicit-detail-mode";
  }

  typedef acl-open-config-detail-mode {
    type enumeration {
      enum EXPLICIT {
        value 0;
        description
          "EXPLICIT_MODE";
      }
      enum BUILTIN {
        value 1;
        description
          "BUILTIN_MODE";
      }
    }
    description
      "acl-open-config-detail-mode";
  }

  typedef acl-open-config-builtin-detail {
    type enumeration {
      enum TCP_INITIAL {
        value 0;
        description
          "TCP_INITIAL";
      }
      enum TCP_ESTABLISHED {
        value 1;
        description
          "TCP_ESTABLISHED";
      }
      enum FRAGMENT {
        value 2;
        description
          "FRAGMENT";
      }
    }
    description
      "acl-open-config-builtin-detail";
  }

  typedef acl-open-config-port-enumns-port-enum {
    type enumeration {
      enum ANY {
        value 0;
        description
          "ANY";
      }
    }
    description
      "acl-open-config-port-enumns-port-enum";
  }

} // main-yang
