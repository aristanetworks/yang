module arista-srte-augments {
  namespace "http://arista.com/yang/openconfig/policy-forwarding/augments";
  prefix arista-srte-augments;

  import openconfig-network-instance {
    prefix oc-netinst;
  }
  import openconfig-pf-srte {
    prefix oc-pf-srte;
  }
  import openconfig-yang-types {
    prefix oc-yang;
  }
  import openconfig-segment-routing {
    prefix "oc-sr";
  }

  organization
    "Arista Networks, Inc.";
  contact
    "Arista Networks, Inc.
    Product Support";
  description
    "This module contains OpenConfig SRTE deviations in Arista EOS.

    Copyright (c) 2019 Arista Networks, Inc. All rights reserved.";

  revision 2019-08-07 {
    description
      "Initial augment file.";
  }

  typedef explicit-null-label-type {
    type enumeration {
      enum IPV4 {
        description
          "Push an IPv4 Explicit NULL label on an unlabeled IPv4 packet";
      }
      enum IPV6 {
        description
          "Push an IPv6 Explicit NULL label on an unlabeled IPv6 packet";
      }
      enum IPV4_IPV6 {
        description
          "Push an IPv4 Explicit NULL label on an unlabeled IPv4 packet;
          Push an IPv6 Explicit NULL label on an unlabeled IPv6 packet";
      }
      enum NONE {
        description
          "No Explicit NULL label will be pushed for both IPv4 and IPv6
          unlabeled packets";
      }
    }
  }

  augment "/oc-netinst:network-instances/oc-netinst:network-instance/oc-netinst:policy-forwarding/oc-netinst:policies/oc-netinst:policy/oc-netinst:rules/oc-netinst:rule/oc-pf-srte:srte/oc-pf-srte:config" {
    leaf explicit-null-label {
      type explicit-null-label-type;
      description
        "Type of explicit null label that is being pushed on an unlabeled
        IP packet. If unspecified, the behaviour of the system is undefined,
        and is subject to local implementation choice.";
      reference
        "draft-ietf-idr-segment-routing-te-policy - Section 2.4.4";
    }
  }

  augment "/oc-netinst:network-instances/oc-netinst:network-instance/oc-netinst:policy-forwarding/oc-netinst:policies/oc-netinst:policy/oc-netinst:rules/oc-netinst:rule/oc-pf-srte:srte/oc-pf-srte:state" {
    leaf explicit-null-label {
      type explicit-null-label-type;
      description
        "Type of explicit null label that is being pushed on an unlabeled
        IP packet. If unspecified, the behaviour of the system is undefined,
        and is subject to local implementation choice.";
      reference
        "draft-ietf-idr-segment-routing-te-policy - Section 2.4.4";
    }
  }

  grouping pf-policy-counters-state {
    description
      "Cumulative counters corresponding to forwarding policy";

    leaf out-pkts {
      type oc-yang:counter64;
      description
        "The cumulative count of all packets transmitted by the local
        system for this forwarding policy.";
    }

    leaf out-octets {
      type oc-yang:counter64;
      description
        "The cumulative count of all bytes transmitted by the local
        system for this forwarding policy.";
    }
  }

  grouping pf-segment-list-counters-state {
    description
      "Grouping that describes the counters corresponding to the segment-lists.";

    leaf index {
      type uint64;
      description
        "Unique integer identifying the segment list within the set of
        segment lists of forwarding policy.";
    }

    leaf out-pkts {
      type oc-yang:counter64;
      description
        "A cumulative counter of the total packets transmitted on
        segment list by the local system.";
    }

    leaf out-octets {
      type oc-yang:counter64;
      description
        "A cumulative counter of the total bytes transmitted on
        segment list by the local system.";
    }
  }

  grouping pf-segment-list-sids {
    description
      "List of SIDs that makes up the segment list";

    container sids {
      config false;
      description
        "Container for the list of SIDs that makes up the
        segment list.";

      list sid {
        key "index";

        leaf index {
          type leafref {
            path "../state/index";
          }
          description
            "Reference to the index leaf which is the key to the list of sid";
        }

        container state {
          leaf index {
            type uint64;
            description
              "The index of the SID within the segment list";
          }

          leaf value {
            type oc-sr:sr-sid-type;
            description
              "The value of the SID that is to be used. Specified as an MPLS
              label or IPv6 address.";
          }
        }
      }
    }
  }

  augment "/oc-netinst:network-instances/oc-netinst:network-instance/oc-netinst:policy-forwarding/oc-netinst:policies/oc-netinst:policy" {
    container policy-counters {
      description
        "This container defines state information for counters per SR-TE policy.";

      container state {
        config false;
        description
          "State parameter for forwarding policy statistics";
        uses pf-policy-counters-state;
      }
    }

    container segment-list-counters {
      config false;
      description
        "This container defines state information for counters per segment-list.";

      list segment-list-counter {
        key "index";

        description
          "Counters for traffic forwarded on a segment list in the local system.";

        leaf index {
          type leafref {
            path "../state/index";
          }
          description
            "Reference to the index leaf which is the key to the list of segment-list";
        }

        container state {
          description
            "Operational state relating to segment-list counters.";
          uses pf-segment-list-counters-state;
        }

        uses pf-segment-list-sids;
      }
    }
  }
}
