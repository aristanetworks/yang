module arista-system-deviations {
  namespace "http://arista.com/yang/openconfig/system/deviations";
  prefix arista-system-deviations;

  import openconfig-system {
    prefix oc-sys;
  }

  organization
    "Arista Networks, Inc.";
  contact
    "Arista Networks, Inc.
     Product Support";
  description
    "This module contains OpenConfig system deviations in Arista EOS.
     Copyright (c) 2017 Arista Networks, Inc. All rights reserved.";

  revision 2017-09-24 {
    description
      "Initial deviations file.";
    reference "1.0.0";
  }

  deviation "/oc-sys:system/oc-sys:dns/oc-sys:config/oc-sys:search" {
    description
      "search limited to 6 domain-names";
    deviate add {
      max-elements "6";
    }
  }
  deviation "/oc-sys:system/oc-sys:dns/oc-sys:servers/oc-sys:server" {
    description
      "name servers limited to 3";
    deviate add {
      max-elements "3";
    }
  }
  deviation "/oc-sys:system/oc-sys:dns/oc-sys:servers/oc-sys:server/oc-sys:config" {
    description
      "port of name servers must be 53";
    deviate add {
      must "port='53'" {
        error-message "port must be 53";
      }
    }
  }
  deviation "/oc-sys:system/oc-sys:dns/oc-sys:host-entries/oc-sys:host-entry/oc-sys:config/oc-sys:alias" {
    description
      "alias of host-entries is not configurable";
    deviate not-supported;
  }
  deviation "/oc-sys:system/oc-sys:memory/oc-sys:state/oc-sys:physical" {
    description
      "physical memory default value 0";
    deviate add {
      default "0";
    }
  }
}
