module arista-rpol-deviations {
  namespace "http://arista.com/yang/openconfig/policy/deviations";
  prefix arista-rpol-deviations;

  import openconfig-routing-policy {
    prefix oc-rpol;
  }
  import openconfig-bgp-policy {
    prefix oc-bgp-pol;
  }
  import openconfig-bgp-types {
    prefix oc-bgp-types;
  }
  import openconfig-ospf-policy {
    prefix oc-ospf-pol;
  }
  import openconfig-isis-policy {
    prefix oc-isis-pol;
  }
  import openconfig-extensions {
    prefix oc-ext;
  }
  import openconfig-isis-types {
    prefix isis-types;
  }

  organization
    "Arista Networks, Inc.";
  contact
    "Arista Networks, Inc.
     Product Support";
  description
    "This module contains OpenConfig routing policy deviations in Arista EOS.

     Copyright (c) 2016 Arista Networks, Inc. All rights reserved.";
  oc-ext:openconfig-version "1.4.0";

  revision 2024-09-12 {
    description
      "Support only IPv4 and IPv6 addresses for set-next-hop";
    reference
      "1.5.0";
  }
  revision 2024-05-31 {
    description
      "Support ANY for match-set-options in policy definition match-tag-set";
    reference
      "1.4.0";
  }
  revision 2024-05-31 {
    description
      "Support INVERT for match-set-options in policy definition (ext)-comm-set";
    reference
      "1.3.0";
  }
  oc-ext:openconfig-version "1.2.0";
  revision 2024-05-20 {
    description
      "support INVERT for prefix-set match-set-options";
    reference
      "1.2.1";
  }
  revision 2024-05-01 {
    description
      "Support LEVEL_1_2 as well for set-level";
    reference
      "1.2.0";
  }
  revision 2024-04-12 {
    description
      "Support only WIDE_METRIC for set-metric-style-type";
    reference
      "1.1.0";
  }
  revision 2024-03-29 {
    description
      "Support only ANY for match-ext-community-set match-set-options";
    reference
      "1.0.10";
  }

  revision 2024-02-27 {
    description
      "Remove set-ext-community reference deviation.";
    reference
      "1.0.9";
  }

  revision 2024-02-06 {
    description
      "Support ANY for prefix-set match-set-options";
    reference
      "1.0.9";
  }

  revision 2024-01-29 {
    description
      "Add restrictions for tag-set.";
    reference
      "1.0.8";
  }
  revision 2024-01-02 {
    description
      "Add description for BGP set-med and OSPF set-metric.";
    reference
      "1.0.8";
  }
  revision 2023-06-21 {
    description
      "Support ALL, ANY, and INVERT for match-set-options.";
    reference
      "1.0.7";
  }
  revision 2023-02-06 {
    description
      "Support ALL and INVERT for match-set-options.";
    reference
      "1.0.6";
  }
  revision 2023-01-26 {
    description
      "Add evpn-es-import-route-target to arista-bgp-ext-community-type.";
    reference
      "1.0.5";
  }
  revision 2022-10-28 {
    description
      "Removed the range from repeat-n leaf.";
      reference
      "1.0.4";
  }
  revision 2022-10-14 {
    description
      "Removed the must constraint for the set-as-path-prepend.";
    reference
      "1.0.3";
  }
  revision 2022-08-16 {
    description
      "Updated the range of repeat-n added the must constraint for the set-as-path-prepend.";
    reference
      "1.0.2";
  }
  revision 2020-11-30 {
    description
      "Fix errors reported by pyang.";
    reference
      "1.0.1";
  }
  revision 2016-02-01 {
    description
      "Initial deviations file.";
    reference
      "1.0.0";
  }

  typedef arista-bgp-set-med-type {
    type union {
      type uint32;
      type string {
        pattern '^[+-][0-9]+$|([0-9]+ )?\+(IGP|METRIC)|METRIC';
      }
      type enumeration {
        enum IGP {
          description
            "set the MED value to the IGP cost toward the
             next hop for the route, only applies for BGP learned routes";
        }
      }
    }
    description
      "Type definition for specifying how the BGP MED can
       be set in BGP policy actions. The three choices are to set
       the MED directly, increment/decrement using +/- notation or
       +IGP or +METRIC or <value> +IGP or <value> +METRIC or METRIC,
       and setting it to the IGP cost (predefined value).";
  }

  typedef arista-bgp-ext-community-type {
    type union {
      type string {
        pattern 'route\-target:'
              + '(6553[0-5]|655[0-2][0-9]|65[0-4][0-9]{2}'
              + '|6[0-4][0-9]{3}|[1-5][0-9]{4}|[1-9][0-9]{1,3}|[0-9]):'
              + '(429496729[0-5]|42949672[0-8][0-9]|4294967[0-1][0-9]{2}'
              + '|429496[0-6][0-9]{3}|42949[0-5][0-9]{4}|4294[0-8][0-9]{5}|'
              + '429[0-3][0-9]{6}|42[0-8][0-9]{7}|4[0-1][0-9]{8}|[1-3][0-9]{9}|'
              + '[1-9][0-9]{1,8}|[0-9])';
      }
      type string {
        pattern 'route\-target:'
              + '(([0-9]|[1-9][0-9]|1[0-9][0-9]|2[0-4][0-9]|'
              + '25[0-5])\.){3}([0-9]|[1-9][0-9]|1[0-9][0-9]|'
              + '2[0-4][0-9]|25[0-5]):'
              + '(6553[0-5]|655[0-2][0-9]|65[0-4][0-9]{2}'
              + '|6[0-4][0-9]{3}|[1-5][0-9]{4}|[1-9][0-9]{1,3}|[0-9])';
      }
      type string {
        pattern 'route\-target:'
              + '(429496729[0-5]|42949672[0-8][0-9]|4294967[0-1][0-9]{2}'
              + '|429496[0-6][0-9]{3}|42949[0-5][0-9]{4}|4294[0-8][0-9]{5}|'
              + '429[0-3][0-9]{6}|42[0-8][0-9]{7}|4[0-1][0-9]{8}|[1-3][0-9]{9}|'
              + '[1-9][0-9]{1,8}|[0-9]):'
              + '(6553[0-5]|655[0-2][0-9]|65[0-4][0-9]{2}'
              + '|6[0-4][0-9]{3}|[1-5][0-9]{4}|[1-9][0-9]{1,3}|[0-9])';
      }
      type string {
        pattern 'route\-origin:'
              + '(6553[0-5]|655[0-2][0-9]|65[0-4][0-9]{2}'
              + '|6[0-4][0-9]{3}|[1-5][0-9]{4}|[1-9][0-9]{1,3}|[0-9]):'
              + '(429496729[0-5]|42949672[0-8][0-9]|4294967[0-1][0-9]{2}'
              + '|429496[0-6][0-9]{3}|42949[0-5][0-9]{4}|4294[0-8][0-9]{5}|'
              + '429[0-3][0-9]{6}|42[0-8][0-9]{7}|4[0-1][0-9]{8}|[1-3][0-9]{9}|'
              + '[1-9][0-9]{1,8}|[0-9])';
      }
      type string {
        pattern 'route\-origin:'
              + '(([0-9]|[1-9][0-9]|1[0-9][0-9]|2[0-4][0-9]|'
              + '25[0-5])\.){3}([0-9]|[1-9][0-9]|1[0-9][0-9]|'
              + '2[0-4][0-9]|25[0-5]):'
              + '(6553[0-5]|655[0-2][0-9]|65[0-4][0-9]{2}'
              + '|6[0-4][0-9]{3}|[1-5][0-9]{4}|[1-9][0-9]{1,3}|[0-9])';
      }
      type string {
        pattern 'route\-origin:'
              + '(429496729[0-5]|42949672[0-8][0-9]|4294967[0-1][0-9]{2}'
              + '|429496[0-6][0-9]{3}|42949[0-5][0-9]{4}|4294[0-8][0-9]{5}|'
              + '429[0-3][0-9]{6}|42[0-8][0-9]{7}|4[0-1][0-9]{8}|[1-3][0-9]{9}|'
              + '[1-9][0-9]{1,8}|[0-9]):'
              + '(6553[0-5]|655[0-2][0-9]|654[0-9]{2}|65[0-4][0-9]{2}'
              + '|6[0-4][0-9]{3}|[1-5][0-9]{4}|[1-9][0-9]{1,3}|[0-9])';
      }
      type string {
        pattern 'evpn\-es\-import\-route\-target:'
              + '([0-9]|[a-f])([0-9]|[a-f]):([0-9]|[a-f])([0-9]|[a-f]):'
              + '([0-9]|[a-f])([0-9]|[a-f]):([0-9]|[a-f])([0-9]|[a-f]):'
              + '([0-9]|[a-f])([0-9]|[a-f]):([0-9]|[a-f])([0-9]|[a-f])';
      }
      type string {
        pattern 'link\-bandwidth:'
              + '(6553[0-5]|655[0-2][0-9]|65[0-4][0-9]{2}'
              + '|6[0-4][0-9]{3}|[1-5][0-9]{4}|[1-9][0-9]{1,3}|[0-9]):'
              + '(429496729[0-5]|42949672[0-8][0-9]|4294967[0-1][0-9]{2}'
              + '|429496[0-6][0-9]{3}|42949[0-5][0-9]{4}|4294[0-8][0-9]{5}|'
              + '429[0-3][0-9]{6}|42[0-8][0-9]{7}|4[0-1][0-9]{8}|[1-3][0-9]{9}|'
              + '[1-9][0-9]{1,8}|[0-9])';
      }
    }
    description
      "EOS supports a subset of the oc-bgp-types:bgp-ext-community-type:
        - route-target:<2b AS>:<4b value> per RFC4360 section 4
        - route-target:<4b IPv4>:<2b value> per RFC4360 section 4
        - route-target:<4b AS>:<2b value> per RFC5668 section 4
        - route-origin:<2b ASN>:<4b value> per RFC4360 section 5
        - route-origin:<4b IPv4>:<2b value> per RFC4360 section 5
        - route-origin:<4b AS>:<2b value> per RFC5668 section 4
       as well as the link bandwidth extended community
        - evpn-es-import-route-target:<1b hex>:<1b hex>:<1b hex>:<1b hex>:<1b hex>:<1b hex> per RFC 7432 section 7.6
        - link-bandwidth:<2b AS>:<4b value> per RFC4360 section 3.1";
  }

  typedef arista-isis-set-level {
    type union {
        type isis-types:level-number;
        type isis-types:level-type;
    }
    description
      "Type definition for specifying how the isis level can be set.
       For compatibility reasons, level-number will be used to suport level1 and level2 values,
       while level-type is used to support LEVEL_1_2 value.";
  }

  deviation "/oc-rpol:routing-policy/oc-rpol:defined-sets/oc-rpol:neighbor-sets" {
    description
      "Neighbor sets are not supported by our routing-policy implementation";
    deviate not-supported;
  }

  deviation "/oc-rpol:routing-policy/oc-rpol:defined-sets/oc-rpol:tag-sets/oc-rpol:tag-set/oc-rpol:config/oc-rpol:tag-value" {
    description
       "tag-value eos restriction. tag-value maybe only be configured with a single value";
    deviate replace {
      type uint32;
    }
    deviate add {
      min-elements 1;
      max-elements 1;
    }
  }

  deviation "/oc-rpol:routing-policy/oc-rpol:policy-definitions/oc-rpol:policy-definition/oc-rpol:statements/oc-rpol:statement/oc-rpol:actions/oc-bgp-pol:bgp-actions/oc-bgp-pol:set-community/oc-bgp-pol:inline/oc-bgp-pol:config/oc-bgp-pol:communities" {
    description
      "Type of the communities leaf-list is a union of uint32, string or an identityref
       but Arista supports having union of uint32, string, an identityref or an enum
       with a single value. Changing existing leaf-list would result in problems with protobuf enabled.";
    deviate not-supported;
  }

  deviation "/oc-rpol:routing-policy/oc-rpol:policy-definitions/oc-rpol:policy-definition/oc-rpol:statements/oc-rpol:statement/oc-rpol:actions/oc-bgp-pol:bgp-actions/oc-bgp-pol:set-community/oc-bgp-pol:inline/oc-bgp-pol:state/oc-bgp-pol:communities" {
    description
      "Type of the communities leaf-list is a union of uint32, string or an identityref
       but Arista supports having union of uint32, string, an identityref or an enum
       with a single value. Changing existing leaf-list would result in problems with protobuf enabled.";
    deviate not-supported;
  }

  deviation "/oc-rpol:routing-policy/oc-rpol:policy-definitions/oc-rpol:policy-definition/oc-rpol:statements/oc-rpol:statement/oc-rpol:actions/oc-bgp-pol:bgp-actions/oc-bgp-pol:set-ext-community/oc-bgp-pol:inline/oc-bgp-pol:config/oc-bgp-pol:communities" {
    description
      "Type of the communities leaf-list is a union of strings and an identityref
       but Arista supports having union of strings or an enum with a single value.
       Changing existing leaf-list type would result in problems with protobuf enabled.";
    deviate not-supported;
  }

  deviation "/oc-rpol:routing-policy/oc-rpol:policy-definitions/oc-rpol:policy-definition/oc-rpol:statements/oc-rpol:statement/oc-rpol:actions/oc-bgp-pol:bgp-actions/oc-bgp-pol:set-ext-community/oc-bgp-pol:inline/oc-bgp-pol:state/oc-bgp-pol:communities" {
    description
      "Type of the communities leaf-list is a union of strings and an identityref
       but Arista supports having union of strings or an enum with a single value.
       Changing existing leaf-list type would result in problems with protobuf enabled.";
    deviate not-supported;
  }

  deviation "/oc-rpol:routing-policy/oc-rpol:policy-definitions/oc-rpol:policy-definition/oc-rpol:statements/oc-rpol:statement/oc-rpol:actions/oc-bgp-pol:bgp-actions/oc-bgp-pol:config/oc-bgp-pol:set-med" {
    description
      "This affects OSPF metric regardless of whether ospf-actions/set-metric is specified";
    deviate replace {
      type arista-rpol-deviations:arista-bgp-set-med-type;
    }
  }

  deviation "/oc-rpol:routing-policy/oc-rpol:policy-definitions/oc-rpol:policy-definition/oc-rpol:statements/oc-rpol:statement/oc-rpol:actions/oc-bgp-pol:bgp-actions/oc-bgp-pol:state/oc-bgp-pol:set-med" {
    description
      "This affects OSPF metric regardless of whether ospf-actions/set-metric is specified";
    deviate replace {
      type arista-rpol-deviations:arista-bgp-set-med-type;
    }
  }

  deviation "/oc-rpol:routing-policy/oc-rpol:defined-sets/oc-bgp-pol:bgp-defined-sets/oc-bgp-pol:ext-community-sets/oc-bgp-pol:ext-community-set/oc-bgp-pol:config/oc-bgp-pol:ext-community-member" {
    deviate replace {
      type union {
        type arista-rpol-deviations:arista-bgp-ext-community-type;
        type oc-bgp-types:bgp-community-regexp-type;
      }
    }
  }

  deviation "/oc-rpol:routing-policy/oc-rpol:policy-definitions/oc-rpol:policy-definition/oc-rpol:statements/oc-rpol:statement/oc-rpol:actions/oc-ospf-pol:ospf-actions/oc-ospf-pol:set-metric/oc-ospf-pol:config/oc-ospf-pol:metric-type" {
    description
      "Specify the type of metric which is to be set by the policy. By default EOS doesn't set it.";
    deviate delete {
      default "EXTERNAL_TYPE_2";
    }
  }

  deviation "/oc-rpol:routing-policy/oc-rpol:policy-definitions/oc-rpol:policy-definition/oc-rpol:statements/oc-rpol:statement/oc-rpol:actions/oc-ospf-pol:ospf-actions/oc-ospf-pol:set-metric/oc-ospf-pol:state/oc-ospf-pol:metric-type" {
    description
      "Specify the type of metric which is to be set by the policy. By default EOS doesn't set it.";
    deviate delete {
      default "EXTERNAL_TYPE_2";
    }
  }

  // ospf-metric range supported on EOS is <0-4294967295> (2^32), expanding YANG value accordingly (which was originally uint16).
  // BGP set-med is also affected by this because EOS lacks a distinction between OSPF/BGP metric

  deviation "/oc-rpol:routing-policy/oc-rpol:policy-definitions/oc-rpol:policy-definition/oc-rpol:statements/oc-rpol:statement/oc-rpol:actions/oc-ospf-pol:ospf-actions/oc-ospf-pol:set-metric/oc-ospf-pol:config/oc-ospf-pol:metric" {
    description
      "This affects BGP set MED regardless of whether bgp-actions/set-med is specified";
    deviate replace {
      type uint32;
    }
  }

  deviation "/oc-rpol:routing-policy/oc-rpol:policy-definitions/oc-rpol:policy-definition/oc-rpol:statements/oc-rpol:statement/oc-rpol:actions/oc-ospf-pol:ospf-actions/oc-ospf-pol:set-metric/oc-ospf-pol:state/oc-ospf-pol:metric" {
    description
      "This affects BGP set MED regardless of whether bgp-actions/set-med is specified";
    deviate replace {
      type uint32;
    }
  }

  deviation "/oc-rpol:routing-policy/oc-rpol:policy-definitions/oc-rpol:policy-definition/oc-rpol:statements/oc-rpol:statement/oc-rpol:conditions/oc-bgp-pol:bgp-conditions/oc-bgp-pol:community-count/oc-bgp-pol:config/oc-bgp-pol:value" {
    description
      "value must be less than or equal to 1024";
    deviate replace {
      type uint32 {
        range "0..1024";
      }
    }
  }

  deviation "/oc-rpol:routing-policy/oc-rpol:policy-definitions/oc-rpol:policy-definition/oc-rpol:statements/oc-rpol:statement/oc-rpol:conditions/oc-bgp-pol:bgp-conditions/oc-bgp-pol:as-path-length/oc-bgp-pol:config/oc-bgp-pol:value" {
    description
      "value must be less than or equal to 4000";
    deviate replace {
      type uint32 {
        range "0..4000";
      }
    }
  }

  deviation "/oc-rpol:routing-policy/oc-rpol:policy-definitions/oc-rpol:policy-definition/oc-rpol:statements/oc-rpol:statement/oc-rpol:conditions/oc-rpol:match-prefix-set/oc-rpol:config" {
    description
      "match-set-options can only be INVERT if a prefix-set is specified";
    deviate add {
      must "oc-rpol:prefix-set != '' or oc-rpol:match-set-options != 'INVERT'" {
        error-message "match-set-options can only be INVERT if a prefix-set is specified";
      }
    }
  }

  deviation "/oc-rpol:routing-policy/oc-rpol:policy-definitions/oc-rpol:policy-definition/oc-rpol:statements/oc-rpol:statement/oc-rpol:conditions/oc-bgp-pol:bgp-conditions/oc-bgp-pol:match-community-set/oc-bgp-pol:config/oc-bgp-pol:match-set-options" {
    description
      "match-set-options can only support ANY or INVERT and with community-set present";
    deviate add {
      must "(../match-set-options = 'ANY' or ../match-set-options = 'INVERT') and ../community-set != ''" {
        error-message "match-set-options can only support ANY or INVERT and with community-set present";
      }
    }
  }

  deviation "/oc-rpol:routing-policy/oc-rpol:policy-definitions/oc-rpol:policy-definition/oc-rpol:statements/oc-rpol:statement/oc-rpol:conditions/oc-bgp-pol:bgp-conditions/oc-bgp-pol:match-ext-community-set/oc-bgp-pol:config/oc-bgp-pol:match-set-options" {
    description
      "match-set-options can only support ANY or INVERT and with ext-community-set present";
    deviate add {
      must "(../match-set-options = 'ANY' or ../match-set-options = 'INVERT') and ../ext-community-set != ''" {
        error-message "match-set-options can only support ANY or INVERT and with ext-community-set present";
      }
    }
  }

  deviation "/oc-rpol:routing-policy/oc-rpol:policy-definitions/oc-rpol:policy-definition/oc-rpol:statements/oc-rpol:statement/oc-rpol:conditions/oc-rpol:match-tag-set/oc-rpol:config/oc-rpol:match-set-options" {
    description
      "match-set-options can only support ANY";
    deviate add {
      must "../match-set-options = 'ANY'" {
        error-message "match-set-options can only be set to ANY";
      }
      default "ANY";
    }
  }

  deviation "/oc-rpol:routing-policy/oc-rpol:policy-definitions/oc-rpol:policy-definition/oc-rpol:statements/oc-rpol:statement/oc-rpol:actions/oc-isis-pol:isis-actions/oc-isis-pol:config/oc-isis-pol:set-metric-style-type" {
    description
      "set-metric-style-type can only support WIDE_METRIC";
    deviate add {
      must "../set-metric-style-type = 'WIDE_METRIC'" {
        error-message "set-metric-style-type can only be set to WIDE_METRIC in EOS";
      }
    }
  }

  deviation "/oc-rpol:routing-policy/oc-rpol:policy-definitions/oc-rpol:policy-definition/oc-rpol:statements/oc-rpol:statement/oc-rpol:actions/oc-isis-pol:isis-actions/oc-isis-pol:config/oc-isis-pol:set-level" {
    description
      "set-level needs to suport LEVEL_1_2 as well.";
    deviate replace {
      type arista-rpol-deviations:arista-isis-set-level;
    }
  }

  deviation "/oc-rpol:routing-policy/oc-rpol:policy-definitions/oc-rpol:policy-definition/oc-rpol:statements/oc-rpol:statement/oc-rpol:actions/oc-isis-pol:isis-actions/oc-isis-pol:state/oc-isis-pol:set-level" {
    description
      "set-level needs to suport LEVEL_1_2 as well.";
    deviate replace {
      type arista-rpol-deviations:arista-isis-set-level;
    }
  }

  deviation "/oc-rpol:routing-policy/oc-rpol:policy-definitions/oc-rpol:policy-definition/oc-rpol:statements/oc-rpol:statement/oc-rpol:actions/oc-bgp-pol:bgp-actions/oc-bgp-pol:config/oc-bgp-pol:set-next-hop" {
    description
      "set-next-hop only supports IPv4 and IPv6 addresses";
    deviate add {
      must "../set-next-hop != 'SELF' and ../set-next-hop != 'PEER_ADDRESS'" {
        error-message "SELF and PEER_ADDRESS are not supported for set-next-hop";
      }
    }
  }
}
