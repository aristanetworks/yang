module arista-pim-deviations {
  namespace "http://arista.com/yang/openconfig/pim/deviations";
  prefix arista-pim-deviations;

  import openconfig-network-instance {
    prefix oc-netinst;
  }
  import openconfig-extensions {
    prefix oc-ext;
  }

  organization
    "Arista Networks, Inc.";
  contact
    "Arista Networks, Inc.
     Product Support";
  description
    "This module contains OpenConfig PIM deviations in Arista EOS.

     Copyright (c) 2024 Arista Networks, Inc. All rights reserved.";
  oc-ext:openconfig-version "1.0.0";

  revision 2024-07-10 {
    description
     "Changed PIM dead-timer type to be a decimal64";
    reference
    "1.0.0";
  }

  deviation "/oc-netinst:network-instances/oc-netinst:network-instance/oc-netinst:protocols/oc-netinst:protocol/oc-netinst:pim/oc-netinst:interfaces/oc-netinst:interface/oc-netinst:config/oc-netinst:dead-timer" {
    description
      "dead timer is a float value 3.5 by default as mandated by RFC7761";
    deviate replace {
      type decimal64 {
          fraction-digits 2;
      }
    }
  }

}
