module arista-l1-open-config-platform-model-aug {
  yang-version 1;
  namespace "http://arista.com/yang/experimental/eos/arista-l1-open-config-platform-model-aug";
  prefix "arista-l1-open-config-platform-model-aug";

  import openconfig-extensions { prefix "oc-ext"; }
  import openconfig-platform { prefix "openconfig-platform"; }
  organization
    "Arista Networks <http://arista.com/>";
  contact
    "Arista Networks <http://arista.com/>";
  description
    "Attributes related to platform parameters

    THIS YANG MODULE WAS GENERATED. DO NOT EDIT THIS FILE.";

  oc-ext:openconfig-version "1.0.0";

  revision "2022-05-12" {
    description
      "Version 1.0.0, generated on 2022-05-12";
    reference "1.0.0";
  }

  grouping platform-state-aug {
    leaf max-module-power {
      type binary {
         length 8;
      }
      description
        "maxModulePower";
    }
    leaf name {
      type string;
      description
        "name of the grouping";
    }
    description
      "Augments for platform channel state attributes";
  }
  grouping platform-aug {
    list state {
      key "name";
      uses platform-state-aug;
      description
        "Augments for the current state of the platform
          attributes";
    }
    leaf name {
      type string;
      description
        "name of the grouping";
    }
    description
      "Container for augmented platform states";
  }
  augment "/openconfig-platform:components/openconfig-platform:component/openconfig-platform:state" {
     uses platform-state-aug;
}
} // main-yang
