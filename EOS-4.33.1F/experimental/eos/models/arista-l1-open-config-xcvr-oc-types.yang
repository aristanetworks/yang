module arista-l1-open-config-xcvr-oc-types {
  yang-version 1;
  namespace "http://arista.com/yang/experimental/eos/arista-l1-open-config-xcvr-oc-types";
  prefix "arista-l1-open-config-xcvr-oc-types";

  import openconfig-extensions { prefix "oc-ext"; }
  organization
    "Arista Networks <http://arista.com/>";
  contact
    "Arista Networks <http://arista.com/>";
  description
    "Attributes related to interface phy components

    THIS YANG MODULE WAS GENERATED. DO NOT EDIT THIS FILE.";

  oc-ext:openconfig-version "1.0.0";

  revision "2023-12-05" {
    description
      "Version 1.0.0, generated on 2023-12-05";
    reference "1.0.0";
  }

  grouping instant-stats {
    leaf instant {
      type binary {
         length 8;
      }
      description
        "instant";
    }
    description
      "InstantStats";
  }
  grouping avg-min-max-instant-stats {
    leaf instant {
      type binary {
         length 8;
      }
      description
        "instant";
    }
    leaf min {
      type binary {
         length 8;
      }
      description
        "min";
    }
    leaf max {
      type binary {
         length 8;
      }
      description
        "max";
    }
    leaf avg {
      type binary {
         length 8;
      }
      description
        "avg";
    }
    leaf interval {
      type uint64;
      description
        "interval";
    }
    description
      "AvgMinMaxInstantStats";
  }
} // main-yang
