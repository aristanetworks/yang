module arista-anic-common-anic-common {
  yang-version 1;
  namespace "http://arista.com/yang/experimental/eos/arista-anic-common-anic-common";
  prefix "arista-anic-common-anic-common";

  import openconfig-extensions { prefix "oc-ext"; }
  import openconfig-yang-types { prefix "openconfig-yang-types"; }
  organization
    "Arista Networks <http://arista.com/>";
  contact
    "Arista Networks <http://arista.com/>";
  description
    "ANIC common types

    THIS YANG MODULE WAS GENERATED. DO NOT EDIT THIS FILE.";

  oc-ext:openconfig-version "0.0.1";

  revision "2024-06-10" {
    description
      "Version 0.0.1, generated on 2024-06-10";
    reference "0.0.1";
  }

  typedef admin-state {
    type enumeration {
      enum ADMIN_UP {
        value 0;
        description
          "Ready to pass packets";
      }
      enum ADMIN_DOWN {
        value 1;
        description
          "Not ready to pass packets";
      }
      enum ADMIN_TESTING {
        value 2;
        description
          "Not ready to pass packets in testing mode";
      }
    }
    description
      "Admin state";
  }
  typedef operational-state {
    type enumeration {
      enum OPER_UNKNOWN {
        value 0;
        description
          "OPER_UNKNOWN";
      }
      enum OPER_UP {
        value 1;
        description
          "OPER_UP";
      }
      enum OPER_DOWN {
        value 2;
        description
          "OPER_DOWN";
      }
      enum OPER_TESTING {
        value 3;
        description
          "OPER_TESTING";
      }
      enum OPER_DORMANT {
        value 4;
        description
          "OPER_DORMANT";
      }
      enum OPER_NOT_PRESENT {
        value 5;
        description
          "OPER_NOT_PRESENT";
      }
      enum OPER_LOWER_LAYER_DOWN {
        value 6;
        description
          "OPER_LOWER_LAYER_DOWN";
      }
    }
    description
      "operational-state";
  }
  typedef ethernet-speed {
    type enumeration {
      enum SPEED_UNKNOWN {
        value 0;
        description
          "SPEED_UNKNOWN";
      }
      enum SPEED_10_MB {
        value 1;
        description
          "SPEED_10_MB";
      }
      enum SPEED_100_MB {
        value 2;
        description
          "SPEED_100_MB";
      }
      enum SPEED_1_GB {
        value 3;
        description
          "SPEED_1_GB";
      }
      enum SPEED_2500_MB {
        value 4;
        description
          "SPEED_2500_MB";
      }
      enum SPEED_5_GB {
        value 5;
        description
          "SPEED_5_GB";
      }
      enum SPEED_10_GB {
        value 6;
        description
          "SPEED_10_GB";
      }
      enum SPEED_25_GB {
        value 7;
        description
          "SPEED_25_GB";
      }
      enum SPEED_40_GB {
        value 8;
        description
          "SPEED_40_GB";
      }
      enum SPEED_50_GB {
        value 9;
        description
          "SPEED_50_GB";
      }
      enum SPEED_100_GB {
        value 10;
        description
          "SPEED_100_GB";
      }
      enum SPEED_200_GB {
        value 11;
        description
          "SPEED_200_GB";
      }
      enum SPEED_400_GB {
        value 12;
        description
          "SPEED_400_GB";
      }
      enum SPEED_600_GB {
        value 13;
        description
          "SPEED_600_GB";
      }
      enum SPEED_800_GB {
        value 14;
        description
          "SPEED_800_GB";
      }
    }
    description
      "ethernet-speed";
  }
  typedef interface-fec {
    type enumeration {
      enum FEC_FC {
        value 0;
        description
          "FEC_FC";
      }
      enum FEC_RS_528 {
        value 1;
        description
          "FEC_RS_528";
      }
      enum FEC_RS_544 {
        value 2;
        description
          "FEC_RS_544";
      }
      enum FEC_RS_5442_X_INTERLEAVE {
        value 3;
        description
          "FEC_RS_5442_X_INTERLEAVE";
      }
      enum FEC_DISABLED {
        value 4;
        description
          "FEC_DISABLED";
      }
    }
    description
      "interface-fec";
  }
  typedef duplex-mode {
    type enumeration {
      enum DUPLEX_UNKNOWN {
        value 0;
        description
          "DUPLEX_UNKNOWN";
      }
      enum DUPLEX_FULL {
        value 1;
        description
          "DUPLEX_FULL";
      }
      enum DUPLEX_HALF {
        value 2;
        description
          "DUPLEX_HALF";
      }
    }
    description
      "duplex-mode";
  }
  typedef agent-type {
    type enumeration {
      enum UNKNOWN {
        value 0;
        description
          "Agent is not initialized";
      }
      enum HOST {
        value 1;
        description
          "Agent is running on a host";
      }
      enum NIC {
        value 2;
        description
          "Agent is running on a NIC";
      }
    }
    description
      "Agent type";
  }
  grouping port-config {
    leaf enabled {
      type boolean;
      description
        "enabled";
    }
    leaf priorities {
      type uint8;
      description
        "priorities";
    }
    description
      "Port Config";
  }
  grouping traffic-class {
    leaf value {
      type uint8;
      description
        "value";
    }
    description
      "traffic-class";
  }
  grouping dscp-config {
    list dscp-to-tc-map {
      key "dscp-to-tc-map-key";
      leaf dscp-to-tc-map-key {
        type uint32;
        description
          "uint32 key for dscp-to-tc-map list.";
      }
      uses traffic-class;
      description
        "DSCP TC map";
    }
    description
      "DSCP TC map";
  }
  grouping ecn-config {
    leaf tc-ecn-enabled {
      type uint16;
      description
        "Ecn enabled";
    }
    description
      "Ecn configuration";
  }
  grouping config {
    container pfc-port-config {
      uses port-config;
      description
        "Pfc port config";
    }
    container dscp-config {
      uses dscp-config;
      description
        "Dscp config";
    }
    container ecn-config {
      uses ecn-config;
      description
        "Ecn config";
    }
    leaf name {
      type string;
      description
        "name of the grouping";
    }
    description
      "Qos configuration";
  }
  grouping lane-index {
    leaf value {
      type uint8;
      description
        "value";
    }
    description
      "lane-index";
  }
  grouping interface-state {
    leaf name {
      type string;
      description
        "name";
    }
    leaf mtu {
      type uint16;
      description
        "mtu";
    }
    leaf description {
      type string;
      description
        "description";
    }
    leaf enabled {
      type boolean;
      description
        "enabled";
    }
    leaf if-index {
      type uint32;
      description
        "if-index";
    }
    leaf admin-status {
      type admin-state;
      description
        "admin-status";
    }
    leaf oper-status {
      type operational-state;
      description
        "oper-status";
    }
    leaf carrier-transitions {
      type uint64;
      description
        "carrier-transitions";
    }
    leaf out-rate {
      type binary {
         length 8;
      }
      description
        "out-rate";
    }
    leaf in-rate {
      type binary {
         length 8;
      }
      description
        "in-rate";
    }
    leaf last-state-change {
      type uint64;
      description
        "last-state-change";
    }
    description
      "Interface state";
  }
  grouping ethernet-interface-state {
    leaf mac-addr {
      type openconfig-yang-types:mac-address;
      description
        "mac-addr";
    }
    leaf hw-mac-address {
      type openconfig-yang-types:mac-address;
      description
        "hw-mac-address";
    }
    leaf auto-negotiate {
      type boolean;
      description
        "auto-negotiate";
    }
    leaf duplex-mode {
      type duplex-mode;
      description
        "duplex-mode";
    }
    leaf port-speed {
      type ethernet-speed;
      description
        "port-speed";
    }
    leaf enable-flow-control {
      type boolean;
      description
        "enable-flow-control";
    }
    leaf fec-mode {
      type interface-fec;
      description
        "fec-mode";
    }
    leaf negotiated-duplex-mode {
      type duplex-mode;
      description
        "negotiated-duplex-mode";
    }
    leaf negotiated-port-speed {
      type ethernet-speed;
      description
        "negotiated-port-speed";
    }
    uses interface-state;
    description
      "Ethernet interface state";
  }
  grouping interface-counters-base {
    leaf last-counters-change {
      type uint64;
      description
        "last-counters-change";
    }
    leaf name {
      type string;
      description
        "name of the grouping";
    }
    description
      "Interface counter";
  }
  grouping interface-counters {
    leaf in-octets {
      type uint64;
      description
        "in-octets";
    }
    leaf in-pkts {
      type uint64;
      description
        "in-pkts";
    }
    leaf in-unicast-pkts {
      type uint64;
      description
        "in-unicast-pkts";
    }
    leaf in-broadcast-pkts {
      type uint64;
      description
        "in-broadcast-pkts";
    }
    leaf in-multicast-pkts {
      type uint64;
      description
        "in-multicast-pkts";
    }
    leaf out-octets {
      type uint64;
      description
        "out-octets";
    }
    leaf out-pkts {
      type uint64;
      description
        "out-pkts";
    }
    leaf out-unicast-pkts {
      type uint64;
      description
        "out-unicast-pkts";
    }
    leaf out-broadcast-pkts {
      type uint64;
      description
        "out-broadcast-pkts";
    }
    leaf out-multicast-pkts {
      type uint64;
      description
        "out-multicast-pkts";
    }
    leaf in-unknown-protos {
      type uint64;
      description
        "in-unknown-protos";
    }
    uses interface-counters-base;
    description
      "Interface counters";
  }
  grouping interface-error-counters {
    leaf in-errors {
      type uint64;
      description
        "in-errors";
    }
    leaf in-discards {
      type uint64;
      description
        "in-discards";
    }
    leaf out-discards {
      type uint64;
      description
        "out-discards";
    }
    leaf out-errors {
      type uint64;
      description
        "out-errors";
    }
    leaf in-fcs-errors {
      type uint64;
      description
        "in-fcs-errors";
    }
    uses interface-counters-base;
    description
      "Interface error counters";
  }
  grouping ethernet-interface-counters {
    leaf in-mac-control-frames {
      type uint64;
      description
        "in-mac-control-frames";
    }
    leaf in-mac-pause-frames {
      type uint64;
      description
        "in-mac-pause-frames";
    }
    leaf in8021q-frames {
      type uint64;
      description
        "in8021q-frames";
    }
    leaf out-mac-control-frames {
      type uint64;
      description
        "out-mac-control-frames";
    }
    leaf out-mac-pause-frames {
      type uint64;
      description
        "out-mac-pause-frames";
    }
    leaf out8021q-frames {
      type uint64;
      description
        "out8021q-frames";
    }
    leaf in-frames64-octets {
      type uint64;
      description
        "in-frames64-octets";
    }
    leaf in-frames65to127-octets {
      type uint64;
      description
        "in-frames65to127-octets";
    }
    leaf in-frames128to255-octets {
      type uint64;
      description
        "in-frames128to255-octets";
    }
    leaf in-frames256to511-octets {
      type uint64;
      description
        "in-frames256to511-octets";
    }
    leaf in-frames512to1023-octets {
      type uint64;
      description
        "in-frames512to1023-octets";
    }
    leaf in-frames1024to1518-octets {
      type uint64;
      description
        "in-frames1024to1518-octets";
    }
    leaf in-frames1523-to-max-octets {
      type uint64;
      description
        "in-frames1523-to-max-octets";
    }
    uses interface-counters;
    description
      "Ethernet interface counters";
  }
  grouping ethernet-interface-error-counters {
    leaf in-jabber-frames {
      type uint64;
      description
        "in-jabber-frames";
    }
    leaf in-oversize-frames {
      type uint64;
      description
        "in-oversize-frames";
    }
    leaf in-undersize-frames {
      type uint64;
      description
        "in-undersize-frames";
    }
    leaf in-fragment-frames {
      type uint64;
      description
        "in-fragment-frames";
    }
    leaf in-crc-errors {
      type uint64;
      description
        "in-crc-errors";
    }
    leaf in-block-errors {
      type uint64;
      description
        "in-block-errors";
    }
    leaf in-carrier-errors {
      type uint64;
      description
        "in-carrier-errors";
    }
    leaf in-interrupted-tx {
      type uint64;
      description
        "in-interrupted-tx";
    }
    leaf in-late-collision {
      type uint64;
      description
        "in-late-collision";
    }
    leaf in-mac-errors-rx {
      type uint64;
      description
        "in-mac-errors-rx";
    }
    leaf in-single-collision {
      type uint64;
      description
        "in-single-collision";
    }
    leaf in-symbol-error {
      type uint64;
      description
        "in-symbol-error";
    }
    leaf in-maxsize-exceeded {
      type uint64;
      description
        "in-maxsize-exceeded";
    }
    leaf out-mac-errors-tx {
      type uint64;
      description
        "out-mac-errors-tx";
    }
    list in-lane-errors {
      key "value";
      leaf value {
        type uint8;
        description
          "value";
      }
      leaf in-lane-errors-value {
        type uint64;
        description
          "Represent the value of an element of in-lane-errors list.";
      }
      description
        "in-lane-errors";
    }
    list out-lane-errors {
      key "value";
      leaf value {
        type uint8;
        description
          "value";
      }
      leaf out-lane-errors-value {
        type uint64;
        description
          "Represent the value of an element of out-lane-errors list.";
      }
      description
        "out-lane-errors";
    }
    uses interface-error-counters;
    description
      "Ethernet interface error counters";
  }
  grouping generic-counter {
    leaf counter-name {
      type string;
      description
        "counter-name";
    }
    leaf counter-description {
      type string;
      description
        "counter-description";
    }
    leaf counter-value {
      type uint64;
      description
        "counter-value";
    }
    leaf name {
      type string;
      description
        "name of the grouping";
    }
    description
      "Generic counter";
  }
  grouping generic-counters {
    leaf counter-type {
      type string;
      description
        "counter-type";
    }
    list counters {
      key "counter-name";
      uses generic-counter;
      description
        "counters";
    }
    uses interface-counters-base;
    description
      "Generic counters";
  }
  grouping intf-config {
    leaf if-index {
      type uint32;
      description
        "if-index";
    }
    container qos-config {
      uses config;
      description
        "qos-config";
    }
    leaf name {
      type string;
      description
        "name of the grouping";
    }
    description
      "Interface config";
  }
  grouping system-information {
    leaf host-name {
      type string;
      description
        "host-name";
    }
    leaf kernel-name {
      type string;
      description
        "kernel-name";
    }
    leaf kernel-release {
      type string;
      description
        "kernel-release";
    }
    leaf kernel-version {
      type string;
      description
        "kernel-version";
    }
    leaf machine {
      type string;
      description
        "machine";
    }
    leaf operating-system {
      type string;
      description
        "operating-system";
    }
    leaf serial-number {
      type string;
      description
        "serial-number";
    }
    leaf model {
      type string;
      description
        "model";
    }
    leaf chassis-id {
      type string;
      description
        "chassis-id";
    }
    leaf driver-version {
      type string;
      description
        "driver-version";
    }
    description
      "system-information";
  }
  grouping nic-agent-description {
    leaf agent-type {
      type agent-type;
      description
        "agent-type";
    }
    leaf agent-version {
      type string;
      description
        "agent-version";
    }
    container nic-system-information {
      uses system-information;
      description
        "nic-system-information";
    }
    container host-system-information {
      uses system-information;
      description
        "host-system-information";
    }
    description
      "nic-agent-description";
  }
  grouping intf-status {
    leaf if-index {
      type uint32;
      description
        "if-index";
    }
    container description {
      uses nic-agent-description;
      description
        "description";
    }
    container pfc-port-config {
      uses port-config;
      description
        "pfc-port-config";
    }
    container dscp-config {
      uses dscp-config;
      description
        "dscp-config";
    }
    container ecn-config {
      uses ecn-config;
      description
        "ecn-config";
    }
    container state {
      uses ethernet-interface-state;
      description
        "state";
    }
    container counters {
      uses ethernet-interface-counters;
      description
        "counters";
    }
    container error-counters {
      uses ethernet-interface-error-counters;
      description
        "error-counters";
    }
    container rdma-counters {
      uses generic-counters;
      description
        "rdma-counters";
    }
    container rdma-error-counters {
      uses generic-counters;
      description
        "rdma-error-counters";
    }
    container rdma-misc-counters {
      uses generic-counters;
      description
        "rdma-misc-counters";
    }
    container pci-counters {
      uses generic-counters;
      description
        "pci-counters";
    }
    list platform-counters {
      key "counter-type";
      uses generic-counters;
      description
        "platform-counters";
    }
    leaf name {
      type string;
      description
        "name of the grouping";
    }
    description
      "intf-status";
  }
} // main-yang
