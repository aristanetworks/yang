module arista-ebra-vlan-tag {
  yang-version 1;
  namespace "http://arista.com/yang/experimental/eos/arista-ebra-vlan-tag";
  prefix "arista-ebra-vlan-tag";

  import openconfig-extensions { prefix "oc-ext"; }
  import arista-ebra-vlan-tpid { prefix "arista-ebra-vlan-tpid"; }
  organization
    "Arista Networks <http://arista.com/>";
  contact
    "Arista Networks <http://arista.com/>";
  description
    "Models for VLAN headers according to IEEE 802.1Q and IEEE 802.1ad

    THIS YANG MODULE WAS GENERATED. DO NOT EDIT THIS FILE.";

  oc-ext:openconfig-version "1.0.0";

  revision "2021-10-20" {
    description
      "Version 1.0.0, generated on 2021-10-20";
    reference "1.0.0";
  }

  grouping vlan-tag {
    leaf vid {
       type uint16{
          range "0..4097";
       }
       
      default 4095;
       description
          "VLAN identifier (VID). Values greater than 4094 have special meaning.";
       }
         leaf tpid {
      type arista-ebra-vlan-tpid:vlan-tpid;
      description
        "Tag protocol identifier (TPID)";
    }
    leaf priority {
       type uint8{
          range "0..15";
       }
       
      default 0;
       description
          "Priority code point (PCP)";
       }
         description
      "A VLAN tag";
  }
  grouping vlan-tag-encap {
    container outer {
      uses vlan-tag;
      description
        "The outermost VLAN tag";
    }
    container inner {
      uses vlan-tag;
      description
        "The second outermost (or inner) VLAN tag";
    }
    description
      "A stack of VLAN tags";
  }
} // main-yang
