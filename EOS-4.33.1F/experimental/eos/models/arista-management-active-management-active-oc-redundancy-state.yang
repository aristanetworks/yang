module arista-management-active-management-active-oc-redundancy-state {
  yang-version 1;
  namespace "http://arista.com/yang/experimental/eos/arista-management-active-management-active-oc-redundancy-state";
  prefix "arista-management-active-management-active-oc-redundancy-state";

  import openconfig-extensions { prefix "oc-ext"; }
  import arista-exp-eos { prefix "arista-exp-eos"; }
  import openconfig-inet-types { prefix "openconfig-inet-types"; }
  import openconfig-interfaces { prefix "openconfig-interfaces"; }
  import openconfig-types { prefix "openconfig-types"; }
  organization
    "Arista Networks <http://arista.com/>";
  contact
    "Arista Networks <http://arista.com/>";
  description
    "Model for management-active redundancy state

    THIS YANG MODULE WAS GENERATED. DO NOT EDIT THIS FILE.";

  oc-ext:openconfig-version "1.0.0";

  revision "2023-01-06" {
    description
      "Version 1.0.0, generated on 2023-01-06";
    reference "1.0.0";
  }

  typedef fallback-delay-value-seconds {
    type union {
      type uint16;
      type fallback-delay-inf;
    }
    description
      "Fallback delay value type, in seconds.";
  }
  identity REDUNDANCY_MODE_BASE {
    description
      "Base identity for redundancy modes for management-active interface.";
  }
  identity REDUNDANCY_DISABLED {
    base "REDUNDANCY_MODE_BASE";
    description
      "Redundancy disabled.";
  }
  identity REDUNDANCY_MONITOR_LINK_STATE {
    base "REDUNDANCY_MODE_BASE";
    description
      "Redundancy enabled with link-state monitor for redundant management links.";
  }
  identity REDUNDANCY_MONITOR_NEIGHBOR {
    base "REDUNDANCY_MODE_BASE";
    description
      "Redundancy enabled with nieghbor reachability monitor via redundant management links.";
  }
  typedef fallback-delay-inf {
    type enumeration {
      enum INFINITY {
        value 0;
        description
          "Infinite fallback delay";
      }
    }
    description
      "Infinite fallback delay";
  }
  grouping monitor-neighbor-state {
    leaf neighbor-address {
      type openconfig-inet-types:ip-address;
      description
        "Neighbor address to be monitored.";
    }
    leaf monitor-interval {
      type uint32;
      default 200;
      description
        "Interval for sending ARP or NS request packets to the neighbor in milliseconds.";
    }
    leaf timeout-multiplier {
      type uint32;
      default 3;
      description
        "Maximum number of missed ARP or NA replies from the neighbor after which the failover occurs.";
    }
    description
      "Top-level grouping for operational state data for neighbor monitor.";
  }
  grouping monitor-neighbor {
    container state {
      uses monitor-neighbor-state;
      description
        "Top-level container for operational state data for neighbor monitor.";
    }
    description
      "Top-level grouping for neighbor monitor data.";
  }
  grouping mgmt-active-redundancy-state {
    leaf redundancy-mode {
      type identityref {
         base "REDUNDANCY_MODE_BASE";
      }
      default REDUNDANCY_DISABLED;
      description
        "Redundancy mode";
    }
    leaf-list interface {
      type openconfig-interfaces:interface-id;
      description
        "Ordered list of redundant management interfaces.";
    }
    leaf fallback-delay {
      type fallback-delay-value-seconds;
      description
        "Delay after which a higher priority management link will be considered to fallback after it has come up. If set to infinity, then dont automatically fallback.";
    }
    leaf active-controller-card {
      type uint32;
      default 4294967295;
      description
        "Active controller card.";
    }
    leaf active-interface {
      type openconfig-interfaces:interface-id;
      description
        "Active management interface.";
    }
    leaf last-redundancy-config-change {
      type openconfig-types:timeticks64;
      description
        "This timestamp indicates the time redundancy configuration was last applied to management-active interface. The value is the timestamp in nanoseconds relativeto the Unix Epoch (Jan 1, 1970 00:00:00 UTC).";
    }
    leaf last-redundancy-link-change {
      type openconfig-types:timeticks64;
      description
        "This timestamp indicates the time active link was last changed for management-active interface. The value is the timestamp in nanoseconds relative to the Unix Epoch (Jan 1, 1970 00:00:00 UTC).";
    }
    description
      "Top-level grouping for management-active interface redundancy state.";
  }
  grouping mgmt-active-redundancy-state-top {
    container state {
      uses mgmt-active-redundancy-state;
      description
        "Top-level container for management-active interface redundancy state";
    }
    container monitor-neighbor {
      uses monitor-neighbor;
      description
        "Top-level container for neighbor monitor data.";
    }
    description
      "Top-level grouping for management-active interface redundancy state.";
  }
  augment "/arista-exp-eos:arista" {
    container redundancy {
      container management-active {
        config false;
     uses mgmt-active-redundancy-state-top;
     description
         "management-active container";
      }
       description
         "redundancy container";
      }
  }
} // main-yang
