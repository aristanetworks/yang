module arista-ale-counters-open-config-vxlan-counters {
  yang-version 1;
  namespace "http://arista.com/yang/experimental/eos/arista-ale-counters-open-config-vxlan-counters";
  prefix "arista-ale-counters-open-config-vxlan-counters";

  import openconfig-extensions { prefix "oc-ext"; }
  import arista-exp-eos-vxlan { prefix "arista-exp-eos-vxlan"; }
  import openconfig-inet-types { prefix "openconfig-inet-types"; }
  import openconfig-interfaces { prefix "openconfig-interfaces"; }
  organization
    "Arista Networks <http://arista.com/>";
  contact
    "Arista Networks <http://arista.com/>";
  description
    "VxLan encapsulation decapsulation counters

    THIS YANG MODULE WAS GENERATED. DO NOT EDIT THIS FILE.";

  oc-ext:openconfig-version "1.0.0";

  revision "2023-11-29" {
    description
      "Version 1.0.0, generated on 2023-11-29";
    reference "1.0.0";
  }

  grouping vtep-counter-container {
    leaf encap-pkts {
      type uint64;
      description
        "The total number of packets encapsulated on the local device that are directed towards a specific VTEP.";
    }
    leaf encap-bytes {
      type uint64;
      description
        "The total number of bytes encapsulated on the local device that are directed towards a specific VTEP.";
    }
    leaf decap-pkts {
      type uint64;
      description
        "The total number of packets from a specific VTEP  that are decapsulated on the local device.";
    }
    leaf decap-bytes {
      type uint64;
      description
        "The total number of bytes from a specific VTEP that are decapsulated on the local device.";
    }
    leaf bum-decap-pkts {
      type uint64;
      description
        "The total number of BUM packets from a specific VTEP that are decapsulated on the local device.";
    }
    leaf drop-decap-pkts {
      type uint64;
      description
        "The total number of decapsulated packets from a specific VTEP that have been dropped locally.";
    }
    leaf except-decap-pkts {
      type uint64;
      description
        "The total number of decapsulated packets from a specific  VTEP that hit an exceptional condition.";
    }
    description
      "Operational state regarding traffic encapsulated on local device and directed towards a specific VTEP.";
  }
  grouping vtep-state-container {
    leaf vtep-ip {
      type openconfig-inet-types:ip-address;
      description
        "VTEP IP address";
    }
    container counters {
      uses vtep-counter-container;
      description
        "Operational state for the counter";
    }
    description
      "Operational state for a specific VTEP.";
  }
  grouping vxlan-counter-container {
    list vxlan-counter {
      key "vtep-ip";
      uses vtep-state-container;
      description
        "vxlanCounter collection";
    }
    leaf name {
      type string;
      description
        "name of the grouping";
    }
    description
      "Enclosing container for the list of VTEPs(Virtual Tunnel End Point)";
  }
  augment "/openconfig-interfaces:interfaces/openconfig-interfaces:interface/arista-exp-eos-vxlan:arista-vxlan" {
    container vteps {
      list vtep {
        key "vtep-ip";
        leaf vtep-ip {
          type string;
          description
            "vtep-ip leaf used as key for vtep list";
        }
        container state {
          config false;
     uses vtep-state-container;
     description
         "state container";
      }
       description
         "vtep list";
      }
       description
         "vteps container";
      }
  }
} // main-yang
