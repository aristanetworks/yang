module arista-fhrp-fhrp-config {
  yang-version 1;
  namespace "http://arista.com/yang/experimental/eos/arista-fhrp-fhrp-config";
  prefix "arista-fhrp-fhrp-config";

  import openconfig-extensions { prefix "oc-ext"; }
  import arista-exp-eos { prefix "arista-exp-eos"; }
  import openconfig-inet-types { prefix "openconfig-inet-types"; }
  import openconfig-interfaces { prefix "openconfig-interfaces"; }
  organization
    "Arista Networks <http://arista.com/>";
  contact
    "Arista Networks <http://arista.com/>";
  description
    "Configuration for virtual rounter IP addresses

    THIS YANG MODULE WAS GENERATED. DO NOT EDIT THIS FILE.";

  oc-ext:openconfig-version "1.0.0";

  revision "2023-02-13" {
    description
      "Version 1.0.0, generated on 2023-02-13";
    reference "1.0.0";
  }

  grouping varp-intf-config {
    leaf intf-id {
      type openconfig-interfaces:interface-id;
      description
        "Interface identifier";
    }
    list virtual-ip-addr {
      key "virtual-ip-addr-key";
      leaf virtual-ip-addr-key {
        type openconfig-inet-types:ipv4-prefix;
        description
          "openconfig-inet-types:ipv4-prefix key for virtual-ip-addr list.";
      }
      leaf virtual-ip-addr-value {
        type boolean;
        description
          "Represent the value of an element of virtual-ip-addr list.";
      }
      description
        "List of IPv4 virtual router addresses";
    }
    list virtual-ip6-addr {
      key "virtual-ip6-addr-key";
      leaf virtual-ip6-addr-key {
        type openconfig-inet-types:ipv6-address;
        description
          "openconfig-inet-types:ipv6-address key for virtual-ip6-addr list.";
      }
      leaf virtual-ip6-addr-value {
        type boolean;
        description
          "Represent the value of an element of virtual-ip6-addr list.";
      }
      description
        "List of IPv6 virtual router addresses";
    }
    description
      "Configuration data for VARP on interface";
  }
  grouping varp-config {
    list varp-intf-config {
      key "intf-id";
      uses varp-intf-config;
      description
        "VARP interface configurations";
    }
    description
      "Configuration data for VARP";
  }
  augment "/arista-exp-eos:arista" {
    container varp {
      container config {
     uses varp-config;
     description
         "config container";
      }
       description
         "varp container";
      }
  }
} // main-yang
