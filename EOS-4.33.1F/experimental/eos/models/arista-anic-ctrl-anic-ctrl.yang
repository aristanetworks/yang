module arista-anic-ctrl-anic-ctrl {
  yang-version 1;
  namespace "http://arista.com/yang/experimental/eos/arista-anic-ctrl-anic-ctrl";
  prefix "arista-anic-ctrl-anic-ctrl";

  import openconfig-extensions { prefix "oc-ext"; }
  import arista-anic-common-anic-common { prefix "arista-anic-common-anic-common"; }
  import arista-arnet-vrf-name { prefix "arista-arnet-vrf-name"; }
  import arista-exp-eos { prefix "arista-exp-eos"; }
  import openconfig-inet-types { prefix "openconfig-inet-types"; }
  import openconfig-interfaces { prefix "openconfig-interfaces"; }
  organization
    "Arista Networks <http://arista.com/>";
  contact
    "Arista Networks <http://arista.com/>";
  description
    "ANIC aggregated config status

    THIS YANG MODULE WAS GENERATED. DO NOT EDIT THIS FILE.";

  oc-ext:openconfig-version "0.0.1";

  revision "2024-06-11" {
    description
      "Version 0.0.1, generated on 2024-06-11";
    reference "0.0.1";
  }

  typedef state-enum {
    type enumeration {
      enum NOT_CONFIGURED {
        value 0;
        description
          "NOT_CONFIGURED";
      }
      enum NOT_ACTIVE {
        value 1;
        description
          "NOT_ACTIVE";
      }
      enum CONNECTION_PENDING {
        value 2;
        description
          "CONNECTION_PENDING";
      }
      enum CONNECTION_ERROR {
        value 3;
        description
          "CONNECTION_ERROR";
      }
      enum CONNECTED {
        value 4;
        description
          "CONNECTED";
      }
    }
    description
      "state-enum";
  }
  typedef nic-config-sync-state {
    type enumeration {
      enum SYNC_DISABLED {
        value 0;
        description
          "SYNC_DISABLED";
      }
      enum OUT_OF_SYNC {
        value 1;
        description
          "OUT_OF_SYNC";
      }
      enum IN_SYNC {
        value 2;
        description
          "IN_SYNC";
      }
    }
    description
      "nic-config-sync-state";
  }
  grouping anic-management-state {
    description
      "anic-management-state";
  }
  grouping anic-management-info {
    leaf addr {
      type openconfig-inet-types:ip-address;
      description
        "addr";
    }
    leaf vrf-name {
      type arista-arnet-vrf-name:vrf-name;
      description
        "vrf-name";
    }
    leaf port {
      type openconfig-inet-types:port-number;
      description
        "port";
    }
    leaf interface-id {
      type uint8;
      default 1;
      description
        "interface-id";
    }
    description
      "anic-management-info";
  }
  grouping anic-status {
    leaf intf-id {
      type openconfig-interfaces:interface-id;
      description
        "Interface directly attached to the NIC";
    }
    leaf anic-profile-name {
      type string;
      description
        "profile name";
    }
    container management-state {
      uses anic-management-state;
      description
        "management-state";
    }
    container management-info {
      uses anic-management-info;
      description
        "management-info";
    }
    leaf subscriber-status-state {
      type string;
      description
        "subscriber-status-state";
    }
    leaf subscriber-status-reason {
      type string;
      description
        "subscriber-status-reason";
    }
    leaf sync-pfc-state {
      type nic-config-sync-state;
      description
        "sync-pfc-state";
    }
    leaf sync-dscp-state {
      type nic-config-sync-state;
      description
        "sync-dscp-state";
    }
    leaf sync-ecn-state {
      type nic-config-sync-state;
      description
        "sync-ecn-state";
    }
    container nic-agent-description {
      uses arista-anic-common-anic-common:nic-agent-description;
      description
        "agent description";
    }
    container pfc-port-config {
      uses arista-anic-common-anic-common:port-config;
      description
        "PFC port config";
    }
    container dscp-config {
      uses arista-anic-common-anic-common:dscp-config;
      description
        "DSCP config";
    }
    leaf name {
      type string;
      description
        "name of the grouping";
    }
    description
      "status of a single NIC";
  }
  grouping all-anic-status {
    list anic-status {
      key "intf-id";
      uses anic-status;
      description
        "collection of NIC statuses";
    }
    leaf name {
      type string;
      description
        "name of the grouping";
    }
    description
      "Aggregated NIC config status";
  }
  augment "/arista-exp-eos:arista" {
    container interface {
      container anic {
        container status {
          config false;
     uses all-anic-status;
     description
         "status container";
      }
       description
         "anic container";
      }
       description
         "interface container";
      }
  }
} // main-yang
