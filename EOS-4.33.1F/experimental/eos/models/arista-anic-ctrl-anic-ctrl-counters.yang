module arista-anic-ctrl-anic-ctrl-counters {
  yang-version 1;
  namespace "http://arista.com/yang/experimental/eos/arista-anic-ctrl-anic-ctrl-counters";
  prefix "arista-anic-ctrl-anic-ctrl-counters";

  import openconfig-extensions { prefix "oc-ext"; }
  import arista-exp-eos { prefix "arista-exp-eos"; }
  import openconfig-interfaces { prefix "openconfig-interfaces"; }
  organization
    "Arista Networks <http://arista.com/>";
  contact
    "Arista Networks <http://arista.com/>";
  description
    "ANIC aggregated status counters

    THIS YANG MODULE WAS GENERATED. DO NOT EDIT THIS FILE.";

  oc-ext:openconfig-version "1.0.0";

  revision "2024-05-15" {
    description
      "Version 1.0.0, generated on 2024-05-15";
    reference "1.0.0";
  }

  grouping counter {
    leaf counter-name {
      type string;
      description
        "";
    }
    leaf counter-description {
      type string;
      description
        "";
    }
    leaf counter-value {
      type uint64;
      description
        "";
    }
    description
      "";
  }
  grouping counters {
    leaf counter-type {
      type string;
      description
        "";
    }
    list counters {
      key "counter-name";
      uses counter;
      description
        "";
    }
    leaf last-counters-change {
      type uint64;
      description
        "";
    }
    description
      "";
  }
  grouping anic-counters {
    leaf intf-id {
      type openconfig-interfaces:interface-id;
      description
        "interface that is directly attached to a NIC";
    }
    container rdma-counters {
      uses counters;
      description
        "RDMA counter values";
    }
    container rdma-error-counters {
      uses counters;
      description
        "RDMA error counter values";
    }
    container rdma-misc-counters {
      uses counters;
      description
        "RDMA misc counter values";
    }
    container pci-counters {
      uses counters;
      description
        "PCI counter values";
    }
    list platform-counters {
      key "counter-type";
      uses counters;
      description
        "Platform specific counter values";
    }
    description
      "Counters container";
  }
  grouping all-anic-counters {
    list anic-counters {
      key "intf-id";
      uses anic-counters;
      description
        "Counter values for the directly attached NICs";
    }
    leaf name {
      type string;
      description
        "name of the grouping";
    }
    description
      "ANIC aggregated status counters";
  }
  augment "/arista-exp-eos:arista" {
    container anic {
      container counters {
        config false;
     uses all-anic-counters;
     description
         "counters container";
      }
       description
         "anic container";
      }
  }
} // main-yang
