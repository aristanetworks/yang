module arista-arnet-rate {
  yang-version 1;
  namespace "http://arista.com/yang/experimental/eos/arista-arnet-rate";
  prefix "arista-arnet-rate";

  import openconfig-extensions { prefix "oc-ext"; }
  organization
    "Arista Networks <http://arista.com/>";
  contact
    "Arista Networks <http://arista.com/>";
  description
    "Defines rates types

    THIS YANG MODULE WAS GENERATED. DO NOT EDIT THIS FILE.";

  oc-ext:openconfig-version "0.1.0";

  revision "2023-08-15" {
    description
      "Version 0.1.0, generated on 2023-08-15";
    reference "0.1.0";
  }

  typedef bits-per-second {
    type binary {
      length 8;
    }
    description
      "bits per second";
  }
  typedef packets-per-second {
    type binary {
      length 8;
    }
    description
      "packets per second";
  }
} // main-yang
