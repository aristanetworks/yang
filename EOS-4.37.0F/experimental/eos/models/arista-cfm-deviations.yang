module arista-cfm-deviations {
  namespace "http://arista.com/yang/openconfig/cfm/deviations";
  prefix arista-cfm-deviations;

  import openconfig-oam {
    prefix oc-oam;
  }
  import openconfig-oam-cfm {
    prefix oc-oam-cfm;
  }
  import openconfig-extensions {
    prefix oc-ext;
  }

  organization
    "Arista Networks, Inc.";
  contact
    "Arista Networks, Inc.
     Product Support";
  description
    "This module contains OpenConfig CFM deviations in Arista EOS.

     Copyright (c) 2026 Arista Networks, Inc. All rights reserved.";
  oc-ext:openconfig-version "1.0.0";

  revision 2026-06-22 {
    description
      "Initial deviation file.";
    reference
      "1.0.0";
  }

  typedef cfm-identifier-string {
    type string {
      length "1..255";
      pattern '[ !#-~]*';
      oc-ext:posix-pattern '^[ !#-~]*$';
    }
    description
      "All printable ASCII characters except double quotes,
       including spaces.";
  }

  deviation "/oc-oam:oam/oc-oam-cfm:cfm/oc-oam-cfm:domains/oc-oam-cfm:maintenance-domain/oc-oam-cfm:config/oc-oam-cfm:md-id" {
    description
      "In EOS, md-id accepts all printable ASCII characters except
       double quotes, including spaces.";
    deviate replace {
      type cfm-identifier-string;
    }
  }

  deviation "/oc-oam:oam/oc-oam-cfm:cfm/oc-oam-cfm:domains/oc-oam-cfm:maintenance-domain/oc-oam-cfm:state/oc-oam-cfm:md-id" {
    description
      "In EOS, md-id accepts all printable ASCII characters except
       double quotes, including spaces.";
    deviate replace {
      type cfm-identifier-string;
    }
  }

  deviation "/oc-oam:oam/oc-oam-cfm:cfm/oc-oam-cfm:domains/oc-oam-cfm:maintenance-domain/oc-oam-cfm:maintenance-associations/oc-oam-cfm:maintenance-association/oc-oam-cfm:config/oc-oam-cfm:ma-id" {
    description
      "In EOS, ma-id accepts all printable ASCII characters except
       double quotes, including spaces.";
    deviate replace {
      type cfm-identifier-string;
    }
  }

  deviation "/oc-oam:oam/oc-oam-cfm:cfm/oc-oam-cfm:domains/oc-oam-cfm:maintenance-domain/oc-oam-cfm:maintenance-associations/oc-oam-cfm:maintenance-association/oc-oam-cfm:state/oc-oam-cfm:ma-id" {
    description
      "In EOS, ma-id accepts all printable ASCII characters except
       double quotes, including spaces.";
    deviate replace {
      type cfm-identifier-string;
    }
  }
}
