module arista-ebra-sub-intf {
  yang-version 1;
  namespace "http://arista.com/yang/experimental/eos/arista-ebra-sub-intf";
  prefix "arista-ebra-sub-intf";
  
  import openconfig-extensions { prefix "oc-ext"; }
  
  organization
    "Arista Networks <http://arista.com/>";
  contact
    "Arista Networks <http://arista.com/>";
  
  description
    "Attributes related to sub-interfaces
    THIS YANG MODULE WAS GENERATED. DO NOT EDIT THIS FILE.";
  
  oc-ext:openconfig-version "1.0.0";
  
  revision "2025-10-20" {
    description
      "Version 1.0.0, generated on 2025-10-20";
    reference "1.0.0";
  }
  grouping interface-sub-intf-key {
    leaf parent-intf-name {
      type string;
      description
        "The parent interface name (eg, EthernetX/Y)";
    }
    leaf index {
      type uint32;
      description
        "The index of the sub-interface";
    }
    description
      "Key for a sub-interface attribute";
  }
} // main-yang
