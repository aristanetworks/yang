module arista-inband-telemetry-common-ifa-flow-table-open-config {
  yang-version 1;
  namespace "http://arista.com/yang/experimental/eos/arista-inband-telemetry-common-ifa-flow-table-open-config";
  prefix "arista-inband-telemetry-common-ifa-flow-table-open-config";
  
  import openconfig-extensions { prefix "oc-ext"; }
  import arista-eos-types { prefix "arista-eos-types"; }
  import arista-exp-eos { prefix "arista-exp-eos"; }
  import openconfig-inet-types { prefix "openconfig-inet-types"; }
  import openconfig-packet-match-types { prefix "openconfig-packet-match-types"; }
  import openconfig-yang-types { prefix "openconfig-yang-types"; }
  
  organization
    "Arista Networks <http://arista.com/>";
  contact
    "Arista Networks <http://arista.com/>";
  
  description
    "YANG model exposing In-band Flow Analyzer (IFA) telemetry. For each configured flow tracker the model lists the monitored IPv4 and IPv6 flows, reporting the captured Layer-2/3/4 record, Border Gateway Protocol (BGP) routing context, RDMA over Converged Ethernet version 2 (RoCEv2) counters, per-hop measurements along the IFA path, and statistics aggregated across recent observation intervals.
    THIS YANG MODULE WAS GENERATED. DO NOT EDIT THIS FILE.";
  
  oc-ext:openconfig-version "1.0.0";
  
  revision "2026-06-07" {
    description
      "Version 1.0.0, generated on 2026-06-07";
    reference "1.0.0";
  }
  typedef inband-telemetry-open-config-ifa-node-index {
    type uint8 {
      range "0..4";
    }
    default 0;
    description
      "Index of a hop along the IFA-monitored path.";
  }
  typedef inband-telemetry-open-config-ifa-global-interval-index {
    type uint8 {
      range "0..9";
    }
    default 0;
    description
      "Index of an aggregation interval for path-wide stats.";
  }
  typedef inband-telemetry-open-config-ifa-node-interval-index {
    type uint8 {
      range "0..49";
    }
    default 0;
    description
      "Index of a per-hop statistics entry collected during one aggregation interval. The hop and interval that this index identifies are also reported as their own fields on each entry.";
  }
  typedef inband-telemetry-open-config-ifa-flow-direction {
    type enumeration {
      enum BIDIRECTIONAL {
        value 0;
        description
          "Flow observed entering and leaving the interface.";
      }
      enum INGRESS {
        value 1;
        description
          "Flow observed entering the interface.";
      }
      enum EGRESS {
        value 2;
        description
          "Flow observed leaving the interface.";
      }
    }
    description
      "Direction in which the flow was observed.";
  }
  typedef inband-telemetry-open-config-ifa-flow-end-reason {
    type enumeration {
      enum ACTIVE_TIMEOUT {
        value 0;
        description
          "Active timer expired while the flow was still receiving traffic.";
      }
      enum IDLE_TIMEOUT {
        value 1;
        description
          "No traffic matched the flow for the idle-timeout interval.";
      }
    }
    description
      "Reason a flow record was exported.";
  }
  grouping inband-telemetry-open-config-ifa-node-state {
    leaf node-key {
      type inband-telemetry-open-config-ifa-node-index;
      description
        "Position of this hop within the IFA path.";
    }
    leaf device-id {
      type uint32;
      description
        "Device identifier reported by this node.";
    }
    leaf ingress-port {
      type uint16;
      description
        "Ingress port identifier at this hop.";
    }
    leaf egress-port {
      type uint16;
      description
        "Egress port identifier at this hop.";
    }
    leaf egress-queue-id {
      type uint32;
      description
        "Egress queue identifier used at this hop.";
    }
    leaf ttl {
      type uint8;
      description
        "IP TTL value observed at this hop.";
    }
    leaf congestion {
      type boolean;
      description
        "When true, this hop reported egress congestion.";
    }
    leaf latency {
      type uint32;
      units nanoseconds;
      description
        "Per-hop latency at this node.";
    }
    description
      "Per-hop IFA metadata captured at one node.";
  }
  grouping inband-telemetry-open-config-ifa-global-interval-state {
    leaf global-interval-stat-key {
      type inband-telemetry-open-config-ifa-global-interval-index;
      description
        "Aggregation-interval index for these counters.";
    }
    leaf interval-start-time {
      type arista-eos-types:seconds;
      description
        "Timestamp at which the interval began. The value is the timestamp in seconds relative to the Unix Epoch (Jan 1, 1970 00:00:00 UTC).";
    }
    leaf num-bytes {
      type uint64;
      units bytes;
      description
        "Total bytes seen on the flow in this interval.";
    }
    leaf num-packets {
      type uint64;
      description
        "Total packets seen on the flow in this interval.";
    }
    description
      "Path-wide counters for one aggregation interval.";
  }
  grouping inband-telemetry-open-config-ifa-node-interval-state {
    leaf node-interval-stat-key {
      type inband-telemetry-open-config-ifa-node-interval-index;
      description
        "Index of this per-hop statistics entry.";
    }
    leaf hop {
      type inband-telemetry-open-config-ifa-node-index;
      description
        "Hop at which these statistics were collected.";
    }
    leaf interval {
      type inband-telemetry-open-config-ifa-global-interval-index;
      description
        "Aggregation interval over which these statistics were collected.";
    }
    leaf congestion {
      type boolean;
      description
        "When true, congestion was seen at this hop this interval.";
    }
    leaf avg-latency {
      type uint32;
      units nanoseconds;
      description
        "Mean latency at this hop.";
    }
    leaf max-latency {
      type uint32;
      units nanoseconds;
      description
        "Maximum latency at this hop.";
    }
    leaf min-latency {
      type uint32;
      units nanoseconds;
      description
        "Minimum latency at this hop.";
    }
    description
      "Per-hop telemetry for one aggregation interval.";
  }
  grouping inband-telemetry-open-config-ifa-node {
    container state {
      uses inband-telemetry-open-config-ifa-node-state;
      config false;
      description
        "Operational state of IFA metadata.";
    }
    description
      "IFA observations at one node along the path.";
  }
  grouping inband-telemetry-open-config-ifa-nodes {
    list node {
      key "node-key";
      leaf node-key {
        type inband-telemetry-open-config-ifa-node-index;
        description
          "inband-telemetry-open-config-ifa-node-index key for node list.";
      }
      uses inband-telemetry-open-config-ifa-node;
      description
        "Per-hop entry keyed by hop index.";
    }
    description
      "Per-hop IFA observations recorded for the flow.";
  }
  grouping inband-telemetry-open-config-ifa-global-interval-stat {
    container state {
      uses inband-telemetry-open-config-ifa-global-interval-state;
      config false;
      description
        "Operational state for this path's aggregation interval.";
    }
    description
      "Path-wide statistics for one aggregation interval.";
  }
  grouping inband-telemetry-open-config-ifa-global-interval-stats {
    list global-interval-stat {
      key "global-interval-stat-key";
      leaf global-interval-stat-key {
        type inband-telemetry-open-config-ifa-global-interval-index;
        description
          "inband-telemetry-open-config-ifa-global-interval-index key for global-interval-stat list.";
      }
      uses inband-telemetry-open-config-ifa-global-interval-stat;
      description
        "Per-interval entry keyed by interval index.";
    }
    description
      "Path-wide statistics retained across recent intervals.";
  }
  grouping inband-telemetry-open-config-ifa-node-interval-stat {
    container state {
      uses inband-telemetry-open-config-ifa-node-interval-state;
      config false;
      description
        "Operational state for this hop's aggregation interval.";
    }
    description
      "Per-hop statistics for one aggregation interval.";
  }
  grouping inband-telemetry-open-config-ifa-node-interval-stats {
    list node-interval-stat {
      key "node-interval-stat-key";
      leaf node-interval-stat-key {
        type inband-telemetry-open-config-ifa-node-interval-index;
        description
          "inband-telemetry-open-config-ifa-node-interval-index key for node-interval-stat list.";
      }
      uses inband-telemetry-open-config-ifa-node-interval-stat;
      description
        "Per-(hop, interval) entry keyed by slot index.";
    }
    description
      "Per-hop statistics retained across recent intervals.";
  }
  grouping inband-telemetry-open-config-ifa-ip4-flow-key {
    leaf vrf-id {
      type uint32;
      description
        "VRF ID in which the flow was observed.";
    }
    leaf vlan-id {
      type uint16;
      description
        "VLAN on which the flow was observed, or 0 if none.";
    }
    leaf direction {
      type inband-telemetry-open-config-ifa-flow-direction;
      description
        "Direction in which the flow was observed.";
    }
    leaf source-address {
      type openconfig-inet-types:ipv4-address;
      description
        "Source IPv4 address of the flow.";
    }
    leaf destination-address {
      type openconfig-inet-types:ipv4-address;
      description
        "Destination IPv4 address of the flow.";
    }
    leaf protocol {
      type openconfig-packet-match-types:ip-protocol-type;
      description
        "IP protocol number of the flow.";
    }
    leaf source-port {
      type openconfig-inet-types:port-number;
      description
        "Layer-4 source port of the flow.";
    }
    leaf destination-port {
      type openconfig-inet-types:port-number;
      description
        "Layer-4 destination port of the flow.";
    }
    description
      "Flow key identifying an IPv4 flow observed by IFA.";
  }
  grouping inband-telemetry-open-config-ifa-ip6-flow-key {
    leaf vrf-id {
      type uint32;
      description
        "VRF ID in which the flow was observed.";
    }
    leaf vlan-id {
      type uint16;
      description
        "VLAN on which the flow was observed, or 0 if none.";
    }
    leaf direction {
      type inband-telemetry-open-config-ifa-flow-direction;
      description
        "Direction in which the flow was observed.";
    }
    leaf source-address {
      type openconfig-inet-types:ipv6-address;
      description
        "Source IPv6 address of the flow.";
    }
    leaf destination-address {
      type openconfig-inet-types:ipv6-address;
      description
        "Destination IPv6 address of the flow.";
    }
    leaf protocol {
      type openconfig-packet-match-types:ip-protocol-type;
      description
        "IP protocol number of the flow.";
    }
    leaf source-port {
      type openconfig-inet-types:port-number;
      description
        "Layer-4 source port of the flow.";
    }
    leaf destination-port {
      type openconfig-inet-types:port-number;
      description
        "Layer-4 destination port of the flow.";
    }
    description
      "Flow key identifying an IPv6 flow observed by IFA.";
  }
  grouping inband-telemetry-open-config-ifa-ip4-flow-state {
    uses inband-telemetry-open-config-ifa-ip4-flow-key;
    leaf path-id {
      type uint32;
      description
        "Identifier of the IFA path traversed by the flow.";
    }
    leaf path-num-bytes {
      type uint64;
      units bytes;
      description
        "Cumulative bytes on the path since first observed.";
    }
    leaf path-num-packets {
      type uint64;
      description
        "Cumulative packets on the path since first observed.";
    }
    leaf path-num-nodes {
      type uint8;
      description
        "Number of hops recorded for this path.";
    }
    leaf path-num-intervals {
      type uint8;
      description
        "Number of aggregation intervals retained.";
    }
    leaf path-overflowed {
      type boolean;
      description
        "When true, the path's hop count exceeded the IFA limit.";
    }
    leaf aggregation-interval {
      type uint32;
      units seconds;
      description
        "Length of one aggregation interval.";
    }
    leaf last-interval-exported-timestamp {
      type arista-eos-types:seconds;
      description
        "Timestamp of the most recently exported interval. The value is the timestamp in seconds relative to the Unix Epoch (Jan 1, 1970 00:00:00 UTC).";
    }
    description
      "Summary of the IFA-monitored path for an IPv4 flow.";
  }
  grouping inband-telemetry-open-config-ifa-ip6-flow-state {
    uses inband-telemetry-open-config-ifa-ip6-flow-key;
    leaf path-id {
      type uint32;
      description
        "Identifier of the IFA path traversed by the flow.";
    }
    leaf path-num-bytes {
      type uint64;
      units bytes;
      description
        "Cumulative bytes on the path since first observed.";
    }
    leaf path-num-packets {
      type uint64;
      description
        "Cumulative packets on the path since first observed.";
    }
    leaf path-num-nodes {
      type uint8;
      description
        "Number of hops recorded for this path.";
    }
    leaf path-num-intervals {
      type uint8;
      description
        "Number of aggregation intervals retained.";
    }
    leaf path-overflowed {
      type boolean;
      description
        "When true, the path's hop count exceeded the IFA limit.";
    }
    leaf aggregation-interval {
      type uint32;
      units seconds;
      description
        "Length of one aggregation interval.";
    }
    leaf last-interval-exported-timestamp {
      type arista-eos-types:seconds;
      description
        "Timestamp of the most recently exported interval. The value is the timestamp in seconds relative to the Unix Epoch (Jan 1, 1970 00:00:00 UTC).";
    }
    description
      "Summary of the IFA-monitored path for an IPv6 flow.";
  }
  grouping inband-telemetry-open-config-ifa-flow-record-state {
    leaf source-mac {
      type openconfig-yang-types:mac-address;
      description
        "Source MAC observed in the flow.";
    }
    leaf destination-mac {
      type openconfig-yang-types:mac-address;
      description
        "Destination MAC observed in the flow.";
    }
    leaf tos {
      type uint8;
      description
        "IP Type-Of-Service octet observed in the flow.";
    }
    leaf tcp-flags {
      type uint8;
      description
        "Bitwise OR of TCP flag bits seen on the flow.";
    }
    leaf bytes {
      type uint64;
      units bytes;
      description
        "Total bytes counted for the flow.";
    }
    leaf packets {
      type uint64;
      description
        "Total packets counted for the flow.";
    }
    leaf start-time {
      type arista-eos-types:seconds;
      description
        "Timestamp of the first packet observed. The value is the timestamp in seconds relative to the Unix Epoch (Jan 1, 1970 00:00:00 UTC).";
    }
    leaf last-packet-time {
      type arista-eos-types:seconds;
      description
        "Timestamp of the most recent packet observed. The value is the timestamp in seconds relative to the Unix Epoch (Jan 1, 1970 00:00:00 UTC).";
    }
    leaf ingress-ifindex {
      type uint32;
      description
        "ifIndex of the ingress interface.";
    }
    leaf egress-ifindex {
      type uint32;
      description
        "ifIndex of the egress interface.";
    }
    leaf ingress-iftype {
      type uint16;
      description
        "Interface-type identifier of the ingress interface. The value is the IANA ifType code as defined in the IANAifType-MIB (RFC 7224), matching the standard YANG type iana-if-type:iana-interface-type (identityref); for example 6 = ethernetCsmacd, 131 = tunnel, 135 = l2vlan, 161 = ieee8023adLag.";
    }
    leaf egress-vlan-id {
      type uint16;
      description
        "VLAN identifier observed on egress.";
    }
    leaf flow-end-reason {
      type inband-telemetry-open-config-ifa-flow-end-reason;
      description
        "Reason that caused the flow record to be exported.";
    }
    description
      "L2/L3/L4 record captured by IFA for the flow.";
  }
  grouping inband-telemetry-open-config-ifa-flow-record {
    container state {
      uses inband-telemetry-open-config-ifa-flow-record-state;
      config false;
      description
        "Captured flow record.";
    }
    description
      "Captured L2/L3/L4 record for the flow.";
  }
  grouping inband-telemetry-open-config-ifa-flow-bgp-info-v4-state {
    leaf source-as {
      type uint32;
      description
        "Autonomous System (AS) originating the source-address route.";
    }
    leaf destination-as {
      type uint32;
      description
        "AS originating the destination-address route.";
    }
    leaf next-hop {
      type openconfig-inet-types:ipv4-address;
      description
        "Forwarding next-hop selected for the flow.";
    }
    leaf bgp-next-hop {
      type openconfig-inet-types:ipv4-address;
      description
        "BGP next-hop advertised for the destination prefix.";
    }
    leaf source-prefix-length {
      type uint8;
      description
        "Prefix length of the source-address route.";
    }
    leaf destination-prefix-length {
      type uint8;
      description
        "Prefix length of the destination-address route.";
    }
    description
      "BGP routing context for an IPv4 flow.";
  }
  grouping inband-telemetry-open-config-ifa-flow-bgp-info-v4 {
    container state {
      uses inband-telemetry-open-config-ifa-flow-bgp-info-v4-state;
      config false;
      description
        "BGP context for the IPv4 flow.";
    }
    description
      "BGP routing context for an IPv4 flow, when available.";
  }
  grouping inband-telemetry-open-config-ifa-flow-bgp-info-v6-state {
    leaf source-as {
      type uint32;
      description
        "Autonomous System (AS) originating the source-address route.";
    }
    leaf destination-as {
      type uint32;
      description
        "AS originating the destination-address route.";
    }
    leaf next-hop {
      type openconfig-inet-types:ipv6-address;
      description
        "Forwarding next-hop selected for the flow.";
    }
    leaf bgp-next-hop {
      type openconfig-inet-types:ipv6-address;
      description
        "BGP next-hop advertised for the destination prefix.";
    }
    leaf source-prefix-length {
      type uint8;
      description
        "Prefix length of the source-address route.";
    }
    leaf destination-prefix-length {
      type uint8;
      description
        "Prefix length of the destination-address route.";
    }
    description
      "BGP routing context for an IPv6 flow.";
  }
  grouping inband-telemetry-open-config-ifa-flow-bgp-info-v6 {
    container state {
      uses inband-telemetry-open-config-ifa-flow-bgp-info-v6-state;
      config false;
      description
        "BGP context for the IPv6 flow.";
    }
    description
      "BGP routing context for an IPv6 flow, when available.";
  }
  grouping inband-telemetry-open-config-ifa-flow-ro-cev2-info-state {
    leaf destination-qp {
      type uint32;
      description
        "RoCEv2 destination queue pair observed.";
    }
    leaf cnp-packets {
      type uint64;
      description
        "Count of Congestion Notification Packets (CNP).";
    }
    leaf ack-packets {
      type uint64;
      description
        "Count of RoCEv2 ACK packets seen on the flow.";
    }
    leaf nack-packets {
      type uint64;
      description
        "Count of RoCEv2 NACK packets seen on the flow.";
    }
    leaf other-packets {
      type uint64;
      description
        "Count of other RoCEv2 packets (not CNP/ACK/NACK).";
    }
    description
      "RDMA over Converged Ethernet version 2 (RoCEv2) counters maintained for the flow.";
  }
  grouping inband-telemetry-open-config-ifa-flow-ro-cev2-info {
    container state {
      uses inband-telemetry-open-config-ifa-flow-ro-cev2-info-state;
      config false;
      description
        "RoCEv2 counters for the flow.";
    }
    description
      "RoCEv2 counters, when RoCEv2 traffic is observed.";
  }
  grouping inband-telemetry-open-config-ifa-ip4-flow-entry {
    uses inband-telemetry-open-config-ifa-ip4-flow-key;
    container state {
      uses inband-telemetry-open-config-ifa-ip4-flow-state;
      config false;
      description
        "Path summary for the IPv4 flow.";
    }
    container flow-record {
      uses inband-telemetry-open-config-ifa-flow-record;
      description
        "Captured L2/L3/L4 record for the flow.";
    }
    container bgp-info {
      uses inband-telemetry-open-config-ifa-flow-bgp-info-v4;
      description
        "BGP routing context for the flow, when available.";
    }
    container rocev2-info {
      uses inband-telemetry-open-config-ifa-flow-ro-cev2-info;
      description
        "RoCEv2 counters, when RoCEv2 traffic is observed.";
    }
    container nodes {
      uses inband-telemetry-open-config-ifa-nodes;
      description
        "Per-hop IFA observations along the flow's path.";
    }
    container global-interval-stats {
      uses inband-telemetry-open-config-ifa-global-interval-stats;
      description
        "Path-wide statistics across recent intervals.";
    }
    container node-interval-stats {
      uses inband-telemetry-open-config-ifa-node-interval-stats;
      description
        "Per-hop statistics across recent intervals.";
    }
    description
      "Per-flow IFA observation record for an IPv4 flow.";
  }
  grouping inband-telemetry-open-config-ifa-ip6-flow-entry {
    uses inband-telemetry-open-config-ifa-ip6-flow-key;
    container state {
      uses inband-telemetry-open-config-ifa-ip6-flow-state;
      config false;
      description
        "Path summary for the IPv6 flow.";
    }
    container flow-record {
      uses inband-telemetry-open-config-ifa-flow-record;
      description
        "Captured L2/L3/L4 record for the flow.";
    }
    container bgp-info {
      uses inband-telemetry-open-config-ifa-flow-bgp-info-v6;
      description
        "BGP routing context for the flow, when available.";
    }
    container rocev2-info {
      uses inband-telemetry-open-config-ifa-flow-ro-cev2-info;
      description
        "RoCEv2 counters, when RoCEv2 traffic is observed.";
    }
    container nodes {
      uses inband-telemetry-open-config-ifa-nodes;
      description
        "Per-hop IFA observations along the flow's path.";
    }
    container global-interval-stats {
      uses inband-telemetry-open-config-ifa-global-interval-stats;
      description
        "Path-wide statistics across recent intervals.";
    }
    container node-interval-stats {
      uses inband-telemetry-open-config-ifa-node-interval-stats;
      description
        "Per-hop statistics across recent intervals.";
    }
    description
      "Per-flow IFA observation record for an IPv6 flow.";
  }
  grouping inband-telemetry-open-config-ifa-ip4-flows {
    list ipv4-flow {
      key "vrf-id vlan-id direction source-address destination-address protocol source-port destination-port";
      uses inband-telemetry-open-config-ifa-ip4-flow-entry;
      description
        "List of monitored IPv4 flows.";
    }
    description
      "IFA-monitored IPv4 flows for one flow tracker.";
  }
  grouping inband-telemetry-open-config-ifa-ip6-flows {
    list ipv6-flow {
      key "vrf-id vlan-id direction source-address destination-address protocol source-port destination-port";
      uses inband-telemetry-open-config-ifa-ip6-flow-entry;
      description
        "List of monitored IPv6 flows.";
    }
    description
      "IFA-monitored IPv6 flows for one flow tracker.";
  }
  augment "/arista-exp-eos:arista/arista-exp-eos:eos" {
    container ifa {
      container trackers {
        list tracker {
          key "name";
          leaf name {
            type string;
            description
              "name leaf used as key for tracker list";
          }
          container ipv4-flows {
            uses inband-telemetry-open-config-ifa-ip4-flows;
            config false;
            description
              "ipv4-flows container";
          }
          container ipv6-flows {
            uses inband-telemetry-open-config-ifa-ip6-flows;
            config false;
            description
              "ipv6-flows container";
          }
          description
            "tracker list";
        }
        description
          "trackers container";
      }
      description
        "ifa container";
    }
  }
} // main-yang
