module arista-fap-memory-state {
  yang-version 1;
  namespace "http://arista.com/yang/experimental/eos/arista-fap-memory-state";
  prefix "arista-fap-memory-state";
  
  import openconfig-extensions { prefix "oc-ext"; }
  import openconfig-platform { prefix "openconfig-platform"; }
  import openconfig-platform-integrated-circuit { prefix "openconfig-platform-integrated-circuit"; }
  
  organization
    "Arista Networks <http://arista.com/>";
  contact
    "Arista Networks <http://arista.com/>";
  
  description
    "YANG model for operational state of memory on Arista device chips.
    THIS YANG MODULE WAS GENERATED. DO NOT EDIT THIS FILE.";
  
  oc-ext:openconfig-version "1.0.0";
  
  revision "2026-01-10" {
    description
      "Version 1.0.0, generated on 2026-01-10";
    reference "1.0.0";
  }
  grouping ale-counters-open-config-memory-metric {
    leaf name {
      type string;
      description
        "Metric name.";
    }
    leaf value {
      type uint64;
      description
        "Metric value.";
    }
    description
      "Individual state metric for Sand memory.";
  }
  grouping ale-counters-open-config-sand-memory-state-metrics {
    list metric {
      key "name";
      uses ale-counters-open-config-memory-metric;
      description
        "Named Sand memory metrics.";
    }
    description
      "Operational state for Sand memory metrics.";
  }
  grouping ale-counters-open-config-sand-memory-state {
    leaf name {
      type string;
      description
        "Memory instance name for this component.";
    }
    container state {
      uses ale-counters-open-config-sand-memory-state-metrics;
      description
        "Operational state data.";
    }
    description
      "Sand memory instance container.";
  }
  augment "/openconfig-platform:components/openconfig-platform:component/openconfig-platform:integrated-circuit/openconfig-platform-integrated-circuit:memory" {
    container vendor {
      container arista {
        container sand {
          uses ale-counters-open-config-sand-memory-state;
          config false;
          description
            "sand container";
        }
        description
          "arista container";
      }
      description
        "vendor container";
    }
  }
} // main-yang
