module arista-ip-rib-aft-filter-open-config {
  yang-version 1;
  namespace "http://arista.com/yang/arista-ip-rib-aft-filter-open-config";
  prefix "arista-ip-rib-aft-filter-open-config";
  
  import openconfig-extensions { prefix "oc-ext"; }
  
  organization
    "Arista Networks <http://arista.com/>";
  contact
    "Arista Networks <http://arista.com/>";
  
  description
    "AFT Streaming RCF POA Container
    THIS YANG MODULE WAS GENERATED. DO NOT EDIT THIS FILE.";
  
  oc-ext:openconfig-version "0.0.0";
  
  revision "2026-04-27" {
    description
      "Version 0.0.0, generated on 2026-04-27";
    reference "0.0.0";
  }
  // covered-by: openconfig-aft-global-filter.yang
  
  grouping open-config-vrf-aft-filter-config {
    leaf ipv4-policy {
      type string;
      description
        "IPv4 policy filter applied to this VRF's AFT entries";
    }
    leaf ipv6-policy {
      type string;
      description
        "IPv6 policy filter applied to this VRF's AFT entries";
    }
    description
      "Per-VRF AFT global filter configuration";
  }
  grouping open-config-vrf-aft-filter {
    container config {
      uses open-config-vrf-aft-filter-config;
      description
        "Configuration parameters for the AFT global filter";
    }
    container state {
      uses open-config-vrf-aft-filter-config;
      config false;
      description
        "Operational state parameters for the AFT global filter";
    }
    description
      "Per-VRF AFT global filter config and state container";
  }
  container network-instances {
    list network-instance {
      key "name";
      oc-ext:telemetry-atomic;
      leaf name {
        type string;
        description
          "name leaf used as key for network-instance list";
      }
      container afts {
        container global-filter {
          uses open-config-vrf-aft-filter;
          description
            "global-filter container";
        }
        oc-ext:telemetry-atomic;
        description
          "afts container";
      }
      description
        "network-instance list";
    }
    oc-ext:telemetry-atomic;
    description
      "network-instances container";
  }
} // main-yang
