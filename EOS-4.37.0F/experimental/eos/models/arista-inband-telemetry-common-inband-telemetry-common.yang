module arista-inband-telemetry-common-inband-telemetry-common {
  yang-version 1;
  namespace "http://arista.com/yang/experimental/eos/arista-inband-telemetry-common-inband-telemetry-common";
  prefix "arista-inband-telemetry-common-inband-telemetry-common";
  
  import openconfig-extensions { prefix "oc-ext"; }
  import arista-exp-eos { prefix "arista-exp-eos"; }
  import arista-inband-telemetry-common-ifa-flow-table-open-config { prefix "arista-inband-telemetry-common-ifa-flow-table-open-config"; }
  
  organization
    "Arista Networks <http://arista.com/>";
  contact
    "Arista Networks <http://arista.com/>";
  
  description
    "YANG model exposing the In-band Flow Analyzer (IFA) state used by external collectors to translate the hardware port identifiers reported in per-hop IFA metadata back to interface names on this switch, and to report the device identifier used by this switch in IFA path records.
    THIS YANG MODULE WAS GENERATED. DO NOT EDIT THIS FILE.";
  
  oc-ext:openconfig-version "1.0.0";
  
  revision "2026-07-15" {
    description
      "Version 1.0.0, generated on 2026-07-15";
    reference "1.0.0";
  }
  grouping inband-telemetry-status {
    leaf enabled {
      type boolean;
      default false;
      description
        "When set to true, IFA is enabled on this switch.";
    }
    leaf device-id {
      type uint32;
      description
        "Device identifier that this switch reports in the per-hop IFA metadata it inserts into IFA packets.";
    }
    description
      "Operational IFA state.";
  }
  grouping inband-telemetry-interface-detail {
    leaf interface-name {
      type string;
      description
        "Name of the interface associated with the hardware port.";
    }
    description
      "Per-interface details recorded in the IFA collector mapping.";
  }
  grouping inband-telemetry-hardware-port-state {
    leaf port-number {
      type uint16;
      description
        "Hardware port number exported in IFA metadata.";
    }
    leaf interface-name {
      type string;
      description
        "Name of the interface associated with the hardware port.";
    }
    description
      "Operational state for one hardware-port mapping entry.";
  }
  grouping inband-telemetry-hardware-port {
    leaf port-number {
      type uint16;
      description
        "Hardware port number exported in IFA metadata.";
    }
    container state {
      uses inband-telemetry-hardware-port-state;
      config false;
      description
        "Operational state for this hardware-port mapping entry.";
    }
    description
      "One hardware-port mapping entry.";
  }
  grouping inband-telemetry-collector-mapping {
    list hardware-port {
      key "port-number";
      uses inband-telemetry-hardware-port;
      description
        "Mapping from hardware port number to the interface details of the corresponding interface on this switch.";
    }
    description
      "Operational IFA state exposed to external collectors.";
  }
  augment "/arista-exp-eos:arista/arista-exp-eos:eos/arista-inband-telemetry-common-ifa-flow-table-open-config:ifa" {
    container state {
      uses inband-telemetry-status;
      config false;
      description
        "state container";
    }
    container hardware-port-mappings {
      uses inband-telemetry-collector-mapping;
      config false;
      description
        "hardware-port-mappings container";
    }
  }
} // main-yang
