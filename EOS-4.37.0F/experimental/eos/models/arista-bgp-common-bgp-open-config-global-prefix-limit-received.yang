module arista-bgp-common-bgp-open-config-global-prefix-limit-received {
  yang-version 1;
  namespace "http://arista.com/yang/arista-bgp-common-bgp-open-config-global-prefix-limit-received";
  prefix "arista-bgp-common-bgp-open-config-global-prefix-limit-received";
  
  import openconfig-extensions { prefix "oc-ext"; }
  import arista-bgp-augments { prefix "arista-bgp-augments"; }
  import openconfig-types { prefix "openconfig-types"; }
  
  organization
    "Arista Networks <http://arista.com/>";
  contact
    "Arista Networks <http://arista.com/>";
  
  description
    "Support for BGP Global prefix-limit-received
    THIS YANG MODULE WAS GENERATED. DO NOT EDIT THIS FILE.";
  
  oc-ext:openconfig-version "2.32.0";
  
  revision "2026-04-30" {
    description
      "Version 2.32.0, generated on 2026-04-30";
    reference "2.32.0";
  }
  // covered-by: openconfig-network-instance.yang,arista-bgp-augments.yang
  
  grouping routing-bgp-open-config-global-prefix-limit-received-config {
    leaf max-prefixes {
      type arista-bgp-augments:max-prefixes-type;
      description
        "max-prefixes";
    }
    leaf prevent-teardown {
      type boolean;
      description
        "prevent-teardown";
    }
    leaf warning-threshold-type {
      type arista-bgp-augments:threshold-type-type;
      description
        "warning-threshold-type";
    }
    leaf warning-threshold {
      type arista-bgp-augments:max-prefixes-type;
      description
        "warning-threshold";
    }
    leaf warning-threshold-pct {
      type openconfig-types:percentage;
      description
        "warning-threshold-pct";
    }
    description
      "routing-bgp-open-config-global-prefix-limit-received-config";
  }
  grouping routing-bgp-open-config-global-prefix-limit-received-container {
    container config {
      uses routing-bgp-open-config-global-prefix-limit-received-config;
      description
        "config";
    }
    container state {
      uses routing-bgp-open-config-global-prefix-limit-received-config;
      config false;
      description
        "state";
    }
    description
      "routing-bgp-open-config-global-prefix-limit-received-container";
  }
  container network-instances {
    list network-instance {
      key "name";
      oc-ext:telemetry-atomic;
      leaf name {
        type string;
        description
          "name leaf used as key for network-instance list";
      }
      container protocols {
        list protocol {
          key "identifier name";
          oc-ext:telemetry-atomic;
          leaf identifier {
            type string;
            description
              "identifier leaf used as key for protocol list";
          }
          leaf name {
            type string;
            description
              "name leaf used as key for protocol list";
          }
          container bgp {
            container global {
              container prefix-limit-received {
                uses routing-bgp-open-config-global-prefix-limit-received-container;
                description
                  "prefix-limit-received container";
              }
              oc-ext:telemetry-atomic;
              description
                "global container";
            }
            oc-ext:telemetry-atomic;
            description
              "bgp container";
          }
          description
            "protocol list";
        }
        oc-ext:telemetry-atomic;
        description
          "protocols container";
      }
      description
        "network-instance list";
    }
    oc-ext:telemetry-atomic;
    description
      "network-instances container";
  }
} // main-yang
