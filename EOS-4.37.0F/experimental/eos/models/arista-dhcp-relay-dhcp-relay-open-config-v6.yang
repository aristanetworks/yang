module arista-dhcp-relay-dhcp-relay-open-config-v6 {
  yang-version 1;
  namespace "http://arista.com/yang/arista-dhcp-relay-dhcp-relay-open-config-v6";
  prefix "arista-dhcp-relay-dhcp-relay-open-config-v6";
  
  import openconfig-extensions { prefix "oc-ext"; }
  import arista-arnet-vrf-name { prefix "arista-arnet-vrf-name"; }
  import openconfig-inet-types { prefix "openconfig-inet-types"; }
  import openconfig-interfaces { prefix "openconfig-interfaces"; }
  
  organization
    "Arista Networks <http://arista.com/>";
  contact
    "Arista Networks <http://arista.com/>";
  
  description
    "Dhcpv6 Relay Model
    THIS YANG MODULE WAS GENERATED. DO NOT EDIT THIS FILE.";
  
  oc-ext:openconfig-version "0.0.0";
  
  revision "2024-08-25" {
    description
      "Version 0.0.0, generated on 2024-08-25";
    reference "0.0.0";
  }
  // covered-by: openconfig-relay-agent.yang,arista-dhcp-relay-dhcp-relay-open-config-v6-augment.yang
  
  typedef ip6-helper-dhcp-relay-open-config-oc-dhcp-relay-local-address-v6 {
    type union {
      type openconfig-inet-types:ipv6-address;
      type openconfig-interfaces:interface-id;
    }
    description
      "ip6-helper-dhcp-relay-open-config-oc-dhcp-relay-local-address-v6";
  }
  typedef ip6-helper-dhcp-relay-open-config-ocdhcp-relay-address-v6 {
    type union {
      type openconfig-inet-types:ipv6-address;
      type string;
    }
    description
      "ip6-helper-dhcp-relay-open-config-ocdhcp-relay-address-v6";
  }
  grouping ip6-helper-dhcp-relay-open-config-ocdhcp-relay-address-v6-vrf-pair {
    leaf address {
      type ip6-helper-dhcp-relay-open-config-ocdhcp-relay-address-v6;
      description
        "address";
    }
    leaf network-instance {
      type arista-arnet-vrf-name:l3-vrf-name;
      description
        "network-instance";
    }
    description
      "ip6-helper-dhcp-relay-open-config-ocdhcp-relay-address-v6-vrf-pair";
  }
  grouping ip6-helper-dhcp-relay-open-config-ocdhcp-relay-intf-key {
    leaf id {
      type string;
      description
        "id";
    }
    description
      "ip6-helper-dhcp-relay-open-config-ocdhcp-relay-intf-key";
  }
  grouping ip6-helper-dhcp-relay-open-config-oc-dhcp-relay-helper-address-v6-config {
    container address-pair {
      uses ip6-helper-dhcp-relay-open-config-ocdhcp-relay-address-v6-vrf-pair;
      description
        "address-pair";
    }
    leaf source-address {
      type ip6-helper-dhcp-relay-open-config-oc-dhcp-relay-local-address-v6;
      description
        "source-address";
    }
    description
      "ip6-helper-dhcp-relay-open-config-oc-dhcp-relay-helper-address-v6-config";
  }
  grouping ip6-helper-dhcp-relay-open-config-oc-dhcp-relay-helper-address-v6 {
    uses ip6-helper-dhcp-relay-open-config-ocdhcp-relay-address-v6-vrf-pair;
    container config {
      uses ip6-helper-dhcp-relay-open-config-oc-dhcp-relay-helper-address-v6-config;
      description
        "config";
    }
    container state {
      uses ip6-helper-dhcp-relay-open-config-oc-dhcp-relay-helper-address-v6-config;
      config false;
      description
        "state";
    }
    description
      "ip6-helper-dhcp-relay-open-config-oc-dhcp-relay-helper-address-v6";
  }
  grouping ip6-helper-dhcp-relay-open-config-oc-dhcp-relay-helper-addresses-v6 {
    list helper-address {
      key "address network-instance";
      uses ip6-helper-dhcp-relay-open-config-oc-dhcp-relay-helper-address-v6;
      description
        "helper-address";
    }
    description
      "ip6-helper-dhcp-relay-open-config-oc-dhcp-relay-helper-addresses-v6";
  }
  grouping ip6-helper-dhcp-relay-open-config-interface-ref-config {
    leaf interface {
      type string;
      description
        "interface";
    }
    leaf subinterface {
      type uint32;
      description
        "subinterface";
    }
    description
      "ip6-helper-dhcp-relay-open-config-interface-ref-config";
  }
  grouping ip6-helper-dhcp-relay-open-config-interface-ref {
    container config {
      uses ip6-helper-dhcp-relay-open-config-interface-ref-config;
      description
        "config";
    }
    container state {
      uses ip6-helper-dhcp-relay-open-config-interface-ref-config;
      config false;
      description
        "state";
    }
    description
      "ip6-helper-dhcp-relay-open-config-interface-ref";
  }
  grouping ip6-helper-dhcp-relay-open-config-interface-config {
    leaf id {
      type openconfig-interfaces:interface-id;
      description
        "id";
    }
    description
      "ip6-helper-dhcp-relay-open-config-interface-config";
  }
  grouping ip6-helper-dhcp-relay-open-config-ocdhcp-relay-v6-intf {
    uses ip6-helper-dhcp-relay-open-config-ocdhcp-relay-intf-key;
    container interface-ref {
      uses ip6-helper-dhcp-relay-open-config-interface-ref;
      description
        "interface-ref";
    }
    container config {
      uses ip6-helper-dhcp-relay-open-config-interface-config;
      description
        "config";
    }
    container state {
      uses ip6-helper-dhcp-relay-open-config-interface-config;
      config false;
      description
        "state";
    }
    description
      "ip6-helper-dhcp-relay-open-config-ocdhcp-relay-v6-intf";
  }
  grouping ip6-helper-dhcp-relay-open-config-ocdhcp-relay-v6 {
    list interface {
      key "id";
      uses ip6-helper-dhcp-relay-open-config-ocdhcp-relay-v6-intf;
      description
        "interface";
    }
    description
      "Dhcp Relay V6 Config";
  }
  container relay-agent {
    container dhcpv6 {
      container interfaces {
        uses ip6-helper-dhcp-relay-open-config-ocdhcp-relay-v6;
        description
          "interfaces container";
      }
      oc-ext:telemetry-atomic;
      description
        "dhcpv6 container";
    }
    oc-ext:telemetry-atomic;
    description
      "relay-agent container";
  }
} // main-yang
