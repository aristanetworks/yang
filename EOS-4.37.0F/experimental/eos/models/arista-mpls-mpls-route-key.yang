module arista-mpls-mpls-route-key {
  yang-version 1;
  namespace "http://arista.com/yang/experimental/eos/arista-mpls-mpls-route-key";
  prefix "arista-mpls-mpls-route-key";
  
  import openconfig-extensions { prefix "oc-ext"; }
  import openconfig-mpls-types { prefix "openconfig-mpls-types"; }
  
  organization
    "Arista Networks <http://arista.com/>";
  contact
    "Arista Networks <http://arista.com/>";
  
  description
    "MPLS route key types
    THIS YANG MODULE WAS GENERATED. DO NOT EDIT THIS FILE.";
  
  oc-ext:openconfig-version "1.0.0";
  
  revision "2026-05-12" {
    description
      "Version 1.0.0, generated on 2026-05-12";
    reference "1.0.0";
  }
  grouping mpls-route-key {
    leaf label {
      type openconfig-mpls-types:mpls-label;
      description
        "label";
    }
    description
      "mpls-route-key";
  }
} // main-yang
