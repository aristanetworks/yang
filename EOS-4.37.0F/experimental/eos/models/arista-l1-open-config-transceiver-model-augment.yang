module arista-l1-open-config-transceiver-model-augment {
  yang-version 1;
  namespace "http://arista.com/yang/arista-l1-open-config-transceiver-model-augment";
  prefix "arista-l1-open-config-transceiver-model-augment";
  
  import openconfig-extensions { prefix "oc-ext"; }
  import arista-l1-open-config-xcvr-oc-types { prefix "arista-l1-open-config-xcvr-oc-types"; }
  import openconfig-platform { prefix "openconfig-platform"; }
  import openconfig-platform-transceiver { prefix "openconfig-platform-transceiver"; }
  import openconfig-transport-types { prefix "openconfig-transport-types"; }
  import openconfig-types { prefix "openconfig-types"; }
  
  organization
    "Arista Networks <http://arista.com/>";
  contact
    "Arista Networks <http://arista.com/>";
  
  description
    "Attributes related to transceiver components
    THIS YANG MODULE WAS GENERATED. DO NOT EDIT THIS FILE.";
  
  oc-ext:openconfig-version "1.0.0";
  
  revision "2022-05-12" {
    description
      "Version 1.0.0, generated on 2022-05-12";
    reference "1.0.0";
  }
  grouping l1-open-config-xcvr-transceiver-state {
    leaf last-update-time {
      type openconfig-types:timeticks64;
      description
        "Performance-monitoring last update time";
    }
    leaf eeprom-checksum-error-detected {
      type boolean;
      default false;
      description
        "eepromChecksumErrorDetected";
    }
    description
      "Container for the state of the transceiver";
  }
  augment "/openconfig-platform:components/openconfig-platform:component/openconfig-platform-transceiver:transceiver/openconfig-platform-transceiver:state" {
    leaf last-update-time {
      type openconfig-types:timeticks64;
      description
        "Performance-monitoring last update time";
    }
    container booster-output-power {
      uses arista-l1-open-config-xcvr-oc-types:l1-open-config-xcvr-instant-stats;
      description
        "The line system egress path output power.";
    }
    container booster-input-power {
      uses arista-l1-open-config-xcvr-oc-types:l1-open-config-xcvr-instant-stats;
      description
        "The line system egress path input power.";
    }
    container pre-amp-output-power {
      uses arista-l1-open-config-xcvr-oc-types:l1-open-config-xcvr-instant-stats;
      description
        "The line system ingress path output power.";
    }
    container pre-amp-input-power {
      uses arista-l1-open-config-xcvr-oc-types:l1-open-config-xcvr-instant-stats;
      description
        "The line system ingress path input power.";
    }
    leaf eeprom-checksum-error-detected {
      type boolean;
      default false;
      description
        "eepromChecksumErrorDetected";
    }
    description
      "lastUpdateTime
      boosterOutputPower
      boosterInputPower
      preAmpOutputPower
      preAmpInputPower
      eepromChecksumErrorDetected";
  }
} // augment-yang
