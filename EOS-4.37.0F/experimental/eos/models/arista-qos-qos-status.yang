module arista-qos-qos-status {
  yang-version 1;
  namespace "http://arista.com/yang/experimental/eos/arista-qos-qos-status";
  prefix "arista-qos-qos-status";
  
  import openconfig-extensions { prefix "oc-ext"; }
  import arista-exp-eos { prefix "arista-exp-eos"; }
  import arista-exp-eos-qos { prefix "arista-exp-eos-qos"; }
  import arista-qos-lib-qos-types { prefix "arista-qos-lib-qos-types"; }
  
  organization
    "Arista Networks <http://arista.com/>";
  contact
    "Arista Networks <http://arista.com/>";
  
  description
    "Yang models for Qos Policy Map Counters
    THIS YANG MODULE WAS GENERATED. DO NOT EDIT THIS FILE.";
  
  oc-ext:openconfig-version "1.0.0";
  
  revision "2025-08-11" {
    description
      "Version 1.0.0, generated on 2025-08-11";
    reference "1.0.0";
  }
  augment "/arista-exp-eos:arista/arista-exp-eos:eos/arista-exp-eos-qos:qos" {
    list pmap {
      key "pmap-name";
      leaf pmap-name {
        type string;
        description
          "pmap-name leaf used as key for pmap list";
      }
      list cmap {
        key "cmap-name";
        leaf cmap-name {
          type string;
          description
            "cmap-name leaf used as key for cmap list";
        }
        container state {
          container policer-aggregate-counters {
            leaf red-pkts {
              config false;
              type uint64;
              description
                "red packets";
            }
            leaf red-bytes {
              config false;
              type uint64;
              description
                "red bytes";
            }
            leaf green-pkts {
              config false;
              type uint64;
              description
                "green packets";
            }
            leaf green-bytes {
              config false;
              type uint64;
              description
                "green bytes";
            }
            leaf yellow-pkts {
              config false;
              type uint64;
              description
                "yellow packets";
            }
            leaf yellow-bytes {
              config false;
              type uint64;
              description
                "yellow bytes";
            }
            description
              "policer-aggregate-counters container";
          }
          list policer-interface-counters {
            key "intf-name";
            config false;
            uses arista-qos-lib-qos-types:qos-policer-counter;
            description
              "policer-interface-counters list";
          }
          description
            "state container";
        }
        description
          "cmap list";
      }
      description
        "pmap list";
    }
  }
} // main-yang
