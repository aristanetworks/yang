module arista-nexthop-group-deviations {
  yang-version 1.1;

  namespace
    "http://arista.com/yang/openconfig/nexthop-group/deviations";
  prefix arista-nexthop-group-deviations;

  import openconfig-network-instance {
    prefix oc-ni;
  }

  import openconfig-extensions {
    prefix oc-ext;
  }

  organization
    "Arista Networks, Inc.";
  contact
    "Arista Networks, Inc.
     Product Support";
  description
    "This module contains OpenConfig static nexthop-group deviations for
     Arista EOS.

     Copyright (c) 2026 Arista Networks, Inc. All rights reserved.";

  oc-ext:openconfig-version "1.0.0";

  revision 2026-08-27 {
    description
      "Restrict UDP encapsulation IP TTL to the EOS-supported range and set
       its default to 64.";
    reference
      "1.0.0";
  }

  deviation
    "/oc-ni:network-instances/oc-ni:network-instance/"
  + "oc-ni:static/oc-ni:next-hops/"
  + "oc-ni:next-hop/oc-ni:encap-headers/"
  + "oc-ni:encap-header/oc-ni:udp-v4/"
  + "oc-ni:config/oc-ni:ip-ttl" {
    description
      "This leaf specifies the IP TTL value used in the outer IPv4 header
       during packet encapsulation. When omitted, it defaults to 64.";
    deviate replace {
      type uint8 {
        range "1..64";
      }
    }
    deviate add {
      default 64;
    }
  }

  deviation
    "/oc-ni:network-instances/oc-ni:network-instance/"
  + "oc-ni:static/oc-ni:next-hops/"
  + "oc-ni:next-hop/oc-ni:encap-headers/"
  + "oc-ni:encap-header/oc-ni:udp-v6/"
  + "oc-ni:config/oc-ni:ip-ttl" {
    description
      "This leaf specifies the IP TTL value used in the outer IPv6 header
       during packet encapsulation. When omitted, it defaults to 64.";
    deviate replace {
      type uint8 {
        range "1..64";
      }
    }
    deviate add {
      default 64;
    }
  }
}
