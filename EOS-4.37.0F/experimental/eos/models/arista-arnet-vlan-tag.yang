module arista-arnet-vlan-tag {
  yang-version 1;
  namespace "http://arista.com/yang/experimental/eos/arista-arnet-vlan-tag";
  prefix "arista-arnet-vlan-tag";
  
  import openconfig-extensions { prefix "oc-ext"; }
  import arista-arnet-vlan-tpid { prefix "arista-arnet-vlan-tpid"; }
  
  organization
    "Arista Networks <http://arista.com/>";
  contact
    "Arista Networks <http://arista.com/>";
  
  description
    "Models for VLAN headers according to IEEE 802.1Q and IEEE 802.1ad
    THIS YANG MODULE WAS GENERATED. DO NOT EDIT THIS FILE.";
  
  oc-ext:openconfig-version "1.0.0";
  
  revision "2021-10-20" {
    description
      "Version 1.0.0, generated on 2021-10-20";
    reference "1.0.0";
  }
  grouping ebra-vlan-tag {
    leaf vid {
      type uint16 {
        range "0..4097";
      }
      default 4095;
      description
        "VLAN identifier (VID). Values greater than 4094 have special meaning.";
    }
    leaf tpid {
      type arista-arnet-vlan-tpid:bridging-vlan-tpid;
      description
        "Tag protocol identifier (TPID)";
    }
    leaf priority {
      type uint8 {
        range "0..15";
      }
      default 0;
      description
        "Priority code point (PCP)";
    }
    description
      "A VLAN tag";
  }
  grouping ebra-vlan-tag-encap {
    container outer {
      uses ebra-vlan-tag;
      description
        "The outermost VLAN tag";
    }
    container inner {
      uses ebra-vlan-tag;
      description
        "The second outermost (or inner) VLAN tag";
    }
    leaf vlan-range-on-inner {
      type boolean;
      description
        "The inner tag is the start of a range.";
    }
    leaf vlan-range-count {
      type uint16;
      default 1;
      description
        "Number of tags in the range.";
    }
    description
      "A stack of VLAN tags";
  }
} // main-yang
