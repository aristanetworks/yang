module arista-sr-te-policy-lib-sr-te-policy-basic-types {
  yang-version 1;
  namespace "http://arista.com/yang/arista-sr-te-policy-lib-sr-te-policy-basic-types";
  prefix "arista-sr-te-policy-lib-sr-te-policy-basic-types";
  
  import openconfig-extensions { prefix "oc-ext"; }
  
  organization
    "Arista Networks <http://arista.com/>";
  contact
    "Arista Networks <http://arista.com/>";
  
  description
    "This is the model for policy forwarding model SrTe extensions types
    THIS YANG MODULE WAS GENERATED. DO NOT EDIT THIS FILE.";
  
  oc-ext:openconfig-version "1.0.0";
  
  revision "2025-12-23" {
    description
      "Version 1.0.0, generated on 2025-12-23";
    reference "1.0.0";
  }
  // covered-by: arista-srte-augments.yang
  
  typedef sr-te-policy-enlp-enum {
    type enumeration {
      enum IPV4 {
        value 1;
        description
          "Push an IPv4 Explicit NULL label on an unlabeled IPv4 packet";
      }
      enum IPV6 {
        value 2;
        description
          "Push an IPv6 Explicit NULL label on an unlabeled IPv6 packet";
      }
      enum IPV4_IPV6 {
        value 3;
        description
          "Push an IPv4 Explicit NULL label on an unlabeled IPv4 packet; Push an IPv6 Explicit NULL label on an unlabeled IPv6 packet";
      }
      enum NONE {
        value 4;
        description
          "No Explicit NULL label will be pushed for both IPv4 and IPv6 unlabeled packets";
      }
    }
    description
      "Type of explicit null label that is being pushed on an unlabeled IP packet.If unspecified, the behaviour of the system is undefined,and is subject to local implementation choice.";
  }
} // main-yang
