module arista-dhcp-relay-dhcp-relay-open-config-v4 {
  yang-version 1;
  namespace "http://arista.com/yang/arista-dhcp-relay-dhcp-relay-open-config-v4";
  prefix "arista-dhcp-relay-dhcp-relay-open-config-v4";
  
  import openconfig-extensions { prefix "oc-ext"; }
  import arista-arnet-vrf-name { prefix "arista-arnet-vrf-name"; }
  import ietf-yang-types { prefix "ietf-yang-types"; }
  import openconfig-inet-types { prefix "openconfig-inet-types"; }
  import openconfig-interfaces { prefix "openconfig-interfaces"; }
  
  organization
    "Arista Networks <http://arista.com/>";
  contact
    "Arista Networks <http://arista.com/>";
  
  description
    "Dhcp Relay Model
    THIS YANG MODULE WAS GENERATED. DO NOT EDIT THIS FILE.";
  
  oc-ext:openconfig-version "0.0.0";
  
  revision "2024-08-25" {
    description
      "Version 0.0.0, generated on 2024-08-25";
    reference "0.0.0";
  }
  // covered-by: openconfig-relay-agent.yang,arista-dhcp-relay-dhcp-relay-open-config-v4-augment.yang
  
  typedef ip-helper-dhcp-relay-open-config-oc-dhcp-relay-local-address {
    type union {
      type openconfig-inet-types:ipv4-address;
      type openconfig-interfaces:interface-id;
    }
    description
      "ip-helper-dhcp-relay-open-config-oc-dhcp-relay-local-address";
  }
  typedef ip-helper-dhcp-relay-open-config-ocdhcp-relay-address {
    type union {
      type openconfig-inet-types:ipv4-address;
      type string;
    }
    description
      "ip-helper-dhcp-relay-open-config-ocdhcp-relay-address";
  }
  grouping ip-helper-dhcp-relay-open-config-ocdhcp-relay-address-vrf-pair {
    leaf address {
      type ip-helper-dhcp-relay-open-config-ocdhcp-relay-address;
      description
        "address";
    }
    leaf network-instance {
      type arista-arnet-vrf-name:l3-vrf-name;
      description
        "network-instance";
    }
    description
      "ip-helper-dhcp-relay-open-config-ocdhcp-relay-address-vrf-pair";
  }
  grouping ip-helper-dhcp-relay-open-config-ocdhcp-relay-intf-key {
    leaf id {
      type string;
      description
        "id";
    }
    description
      "ip-helper-dhcp-relay-open-config-ocdhcp-relay-intf-key";
  }
  grouping ip-helper-dhcp-relay-open-config-oc-dhcp-relay-helper-address-config {
    container address-pair {
      uses ip-helper-dhcp-relay-open-config-ocdhcp-relay-address-vrf-pair;
      description
        "address-pair";
    }
    leaf source-address {
      type ip-helper-dhcp-relay-open-config-oc-dhcp-relay-local-address;
      description
        "source-address";
    }
    description
      "ip-helper-dhcp-relay-open-config-oc-dhcp-relay-helper-address-config";
  }
  grouping ip-helper-dhcp-relay-open-config-oc-dhcp-relay-helper-address {
    uses ip-helper-dhcp-relay-open-config-ocdhcp-relay-address-vrf-pair;
    container config {
      uses ip-helper-dhcp-relay-open-config-oc-dhcp-relay-helper-address-config;
      description
        "config";
    }
    container state {
      uses ip-helper-dhcp-relay-open-config-oc-dhcp-relay-helper-address-config;
      config false;
      description
        "state";
    }
    description
      "ip-helper-dhcp-relay-open-config-oc-dhcp-relay-helper-address";
  }
  grouping ip-helper-dhcp-relay-open-config-oc-dhcp-relay-helper-addresses {
    list helper-address {
      key "address network-instance";
      uses ip-helper-dhcp-relay-open-config-oc-dhcp-relay-helper-address;
      description
        "helper-address";
    }
    description
      "ip-helper-dhcp-relay-open-config-oc-dhcp-relay-helper-addresses";
  }
  grouping ip-helper-dhcp-relay-open-config-interface-ref-config {
    leaf interface {
      type string;
      description
        "interface";
    }
    leaf subinterface {
      type uint32;
      description
        "subinterface";
    }
    description
      "ip-helper-dhcp-relay-open-config-interface-ref-config";
  }
  grouping ip-helper-dhcp-relay-open-config-interface-ref {
    container config {
      uses ip-helper-dhcp-relay-open-config-interface-ref-config;
      description
        "config";
    }
    container state {
      uses ip-helper-dhcp-relay-open-config-interface-ref-config;
      config false;
      description
        "state";
    }
    description
      "ip-helper-dhcp-relay-open-config-interface-ref";
  }
  grouping ip-helper-dhcp-relay-open-config-interface-config {
    leaf id {
      type openconfig-interfaces:interface-id;
      description
        "id";
    }
    description
      "ip-helper-dhcp-relay-open-config-interface-config";
  }
  grouping ip-helper-dhcp-relay-open-config-interface-counter {
    leaf total-dropped {
      type ietf-yang-types:counter64;
      description
        "total-dropped";
    }
    leaf invalid-opcode {
      type ietf-yang-types:counter64;
      description
        "invalid-opcode";
    }
    leaf invalid-options {
      type ietf-yang-types:counter64;
      description
        "invalid-options";
    }
    leaf bootrequest-received {
      type ietf-yang-types:counter64;
      description
        "bootrequest-received";
    }
    leaf dhcp-decline-received {
      type ietf-yang-types:counter64;
      description
        "dhcp-decline-received";
    }
    leaf dhcp-discover-received {
      type ietf-yang-types:counter64;
      description
        "dhcp-discover-received";
    }
    leaf dhcp-inform-received {
      type ietf-yang-types:counter64;
      description
        "dhcp-inform-received";
    }
    leaf dhcp-release-received {
      type ietf-yang-types:counter64;
      description
        "dhcp-release-received";
    }
    leaf dhcp-request-received {
      type ietf-yang-types:counter64;
      description
        "dhcp-request-received";
    }
    leaf bootrequest-sent {
      type ietf-yang-types:counter64;
      description
        "bootrequest-sent";
    }
    leaf bootreply-sent {
      type ietf-yang-types:counter64;
      description
        "bootreply-sent";
    }
    leaf dhcp-offer-sent {
      type ietf-yang-types:counter64;
      description
        "dhcp-offer-sent";
    }
    leaf dhcp-ack-sent {
      type ietf-yang-types:counter64;
      description
        "dhcp-ack-sent";
    }
    leaf dhcp-nack-sent {
      type ietf-yang-types:counter64;
      description
        "dhcp-nack-sent";
    }
    description
      "ip-helper-dhcp-relay-open-config-interface-counter";
  }
  grouping ip-helper-dhcp-relay-open-config-interface-state {
    container counters {
      uses ip-helper-dhcp-relay-open-config-interface-counter;
      description
        "counters";
    }
    uses ip-helper-dhcp-relay-open-config-interface-config;
    description
      "ip-helper-dhcp-relay-open-config-interface-state";
  }
  grouping ip-helper-dhcp-relay-open-config-ocdhcp-relay-intf {
    uses ip-helper-dhcp-relay-open-config-ocdhcp-relay-intf-key;
    container interface-ref {
      uses ip-helper-dhcp-relay-open-config-interface-ref;
      description
        "interface-ref";
    }
    container config {
      uses ip-helper-dhcp-relay-open-config-interface-config;
      description
        "config";
    }
    container state {
      uses ip-helper-dhcp-relay-open-config-interface-state;
      config false;
      description
        "state";
    }
    description
      "ip-helper-dhcp-relay-open-config-ocdhcp-relay-intf";
  }
  grouping ip-helper-dhcp-relay-open-config-ocdhcp-relay {
    list interface {
      key "id";
      uses ip-helper-dhcp-relay-open-config-ocdhcp-relay-intf;
      description
        "interface";
    }
    description
      "Dhcp Relay Config";
  }
  container relay-agent {
    container dhcp {
      container interfaces {
        uses ip-helper-dhcp-relay-open-config-ocdhcp-relay;
        description
          "interfaces container";
      }
      oc-ext:telemetry-atomic;
      description
        "dhcp container";
    }
    oc-ext:telemetry-atomic;
    description
      "relay-agent container";
  }
} // main-yang
