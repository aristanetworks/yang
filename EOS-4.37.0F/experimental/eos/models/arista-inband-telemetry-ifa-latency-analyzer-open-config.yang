module arista-inband-telemetry-ifa-latency-analyzer-open-config {
  yang-version 1;
  namespace "http://arista.com/yang/experimental/eos/arista-inband-telemetry-ifa-latency-analyzer-open-config";
  prefix "arista-inband-telemetry-ifa-latency-analyzer-open-config";
  
  import openconfig-extensions { prefix "oc-ext"; }
  import arista-eos-types { prefix "arista-eos-types"; }
  import arista-exp-eos { prefix "arista-exp-eos"; }
  import openconfig-inet-types { prefix "openconfig-inet-types"; }
  import openconfig-packet-match-types { prefix "openconfig-packet-match-types"; }
  
  organization
    "Arista Networks <http://arista.com/>";
  contact
    "Arista Networks <http://arista.com/>";
  
  description
    "Model for IFA Latency Analyzer
    THIS YANG MODULE WAS GENERATED. DO NOT EDIT THIS FILE.";
  
  oc-ext:openconfig-version "1.0.0";
  
  revision "2026-04-25" {
    description
      "Version 1.0.0, generated on 2026-04-25";
    reference "1.0.0";
  }
  typedef node-index {
    type uint8 {
      range "0..9";
    }
    default 0;
    description
      "IFA node index";
  }
  typedef global-interval-index {
    type uint8 {
      range "0..9";
    }
    default 0;
    description
      "IFA global interval index";
  }
  typedef node-interval-index {
    type uint8 {
      range "0..99";
    }
    default 0;
    description
      "IFA interval index";
  }
  grouping inband-telemetry-open-config-ifa-latency-analyzer-node-state {
    leaf node-key {
      type node-index;
      description
        "node-key";
    }
    leaf device-id {
      type uint32;
      description
        "device-id";
    }
    leaf ingress-port {
      type uint16;
      description
        "ingress-port";
    }
    leaf egress-port {
      type uint16;
      description
        "egress-port";
    }
    leaf congestion {
      type boolean;
      description
        "congestion";
    }
    leaf latency {
      type uint32;
      description
        "latency";
    }
    description
      "Node state";
  }
  grouping inband-telemetry-open-config-ifa-latency-analyzer-global-interval-state {
    leaf global-interval-stat-key {
      type global-interval-index;
      description
        "global-interval-stat-key";
    }
    leaf interval-start-time {
      type arista-eos-types:seconds;
      description
        "interval-start-time";
    }
    leaf num-bytes {
      type uint64;
      description
        "num-bytes";
    }
    leaf num-packets {
      type uint64;
      description
        "num-packets";
    }
    leaf min-path-latency {
      type uint32;
      description
        "min-path-latency";
    }
    leaf avg-path-latency {
      type uint32;
      description
        "avg-path-latency";
    }
    leaf max-path-latency {
      type uint32;
      description
        "max-path-latency";
    }
    leaf min-link-latency {
      type uint32;
      description
        "min-link-latency";
    }
    leaf avg-link-latency {
      type uint32;
      description
        "avg-link-latency";
    }
    leaf max-link-latency {
      type uint32;
      description
        "max-link-latency";
    }
    description
      "Global interval state";
  }
  grouping inband-telemetry-open-config-ifa-latency-analyzer-node-interval-state {
    leaf node-interval-stat-key {
      type node-interval-index;
      description
        "node-interval-stat-key";
    }
    leaf congestion {
      type boolean;
      description
        "congestion";
    }
    leaf avg-latency {
      type uint32;
      description
        "avg-latency";
    }
    leaf max-latency {
      type uint32;
      description
        "max-latency";
    }
    leaf min-latency {
      type uint32;
      description
        "min-latency";
    }
    description
      "Node interval state";
  }
  grouping inband-telemetry-open-config-ifa-latency-analyzer-node {
    container state {
      uses inband-telemetry-open-config-ifa-latency-analyzer-node-state;
      config false;
      description
        "state";
    }
    description
      "inband-telemetry-open-config-ifa-latency-analyzer-node";
  }
  grouping inband-telemetry-open-config-nodes {
    list node {
      key "node-key";
      leaf node-key {
        type node-index;
        description
          "node-index key for node list.";
      }
      uses inband-telemetry-open-config-ifa-latency-analyzer-node;
      description
        "node";
    }
    description
      "inband-telemetry-open-config-nodes";
  }
  grouping inband-telemetry-open-config-ifa-latency-analyzer-global-interval-stats {
    container state {
      uses inband-telemetry-open-config-ifa-latency-analyzer-global-interval-state;
      config false;
      description
        "state";
    }
    description
      "inband-telemetry-open-config-ifa-latency-analyzer-global-interval-stats";
  }
  grouping inband-telemetry-open-config-global-interval-stats {
    list global-interval-stat {
      key "global-interval-stat-key";
      leaf global-interval-stat-key {
        type global-interval-index;
        description
          "global-interval-index key for global-interval-stat list.";
      }
      uses inband-telemetry-open-config-ifa-latency-analyzer-global-interval-stats;
      description
        "global-interval-stat";
    }
    description
      "inband-telemetry-open-config-global-interval-stats";
  }
  grouping inband-telemetry-open-config-ifa-latency-analyzer-node-interval-stats {
    container state {
      uses inband-telemetry-open-config-ifa-latency-analyzer-node-interval-state;
      config false;
      description
        "state";
    }
    description
      "inband-telemetry-open-config-ifa-latency-analyzer-node-interval-stats";
  }
  grouping inband-telemetry-open-config-node-interval-stats {
    list node-interval-stat {
      key "node-interval-stat-key";
      leaf node-interval-stat-key {
        type node-interval-index;
        description
          "node-interval-index key for node-interval-stat list.";
      }
      uses inband-telemetry-open-config-ifa-latency-analyzer-node-interval-stats;
      description
        "node-interval-stat";
    }
    description
      "inband-telemetry-open-config-node-interval-stats";
  }
  grouping inband-telemetry-open-config-ifa-latency-analyzer-ip6-flow-key {
    leaf source-address {
      type openconfig-inet-types:ipv6-address;
      description
        "src-addr";
    }
    leaf destination-address {
      type openconfig-inet-types:ipv6-address;
      description
        "dst-addr";
    }
    leaf protocol {
      type openconfig-packet-match-types:ip-protocol-type;
      description
        "protocol";
    }
    leaf source-port {
      type openconfig-inet-types:port-number;
      description
        "src-port";
    }
    leaf destination-port {
      type openconfig-inet-types:port-number;
      description
        "dst-port";
    }
    description
      "inband-telemetry-open-config-ifa-latency-analyzer-ip6-flow-key";
  }
  grouping inband-telemetry-open-config-ifa-latency-analyzer-ip6-flow-state {
    uses inband-telemetry-open-config-ifa-latency-analyzer-ip6-flow-key;
    leaf path-num-bytes {
      type uint64;
      description
        "path-num-bytes";
    }
    leaf path-num-packets {
      type uint64;
      description
        "path-num-packets";
    }
    leaf path-num-nodes {
      type uint8;
      description
        "path-num-nodes";
    }
    leaf aggregation-interval {
      type arista-eos-types:seconds;
      description
        "aggregation-interval";
    }
    leaf current-interval-index {
      type global-interval-index;
      description
        "current-interval-index";
    }
    description
      "Flow state";
  }
  grouping inband-telemetry-open-config-ifa-latency-analyzer-ip6-flow-entry {
    uses inband-telemetry-open-config-ifa-latency-analyzer-ip6-flow-key;
    container state {
      uses inband-telemetry-open-config-ifa-latency-analyzer-ip6-flow-state;
      config false;
      description
        "state";
    }
    container nodes {
      uses inband-telemetry-open-config-nodes;
      description
        "nodes";
    }
    container global-interval-stats {
      uses inband-telemetry-open-config-global-interval-stats;
      description
        "global-interval-stats";
    }
    container node-interval-stats {
      uses inband-telemetry-open-config-node-interval-stats;
      description
        "node-interval-stats";
    }
    description
      "inband-telemetry-open-config-ifa-latency-analyzer-ip6-flow-entry";
  }
  grouping inband-telemetry-open-config-ifa-latency-analyzer-flow-table {
    list flow {
      key "source-address destination-address protocol source-port destination-port";
      uses inband-telemetry-open-config-ifa-latency-analyzer-ip6-flow-entry;
      description
        "ifa-latency-analyzer-ip6-flow-entry";
    }
    description
      "inband-telemetry-open-config-ifa-latency-analyzer-flow-table";
  }
  augment "/arista-exp-eos:arista/arista-exp-eos:eos" {
    container ifa-latency-analyzer {
      container ipv6-flows {
        uses inband-telemetry-open-config-ifa-latency-analyzer-flow-table;
        config false;
        description
          "ipv6-flows container";
      }
      description
        "ifa-latency-analyzer container";
    }
  }
} // main-yang
