module arista-voq-delete-augment {
  yang-version 1;
  namespace "http://arista.com/yang/arista-voq-delete-augment";
  prefix "arista-voq-delete-augment";
  
  import openconfig-extensions { prefix "oc-ext"; }
  import arista-ale-counters-open-config-qos-interface-queue-common-types { prefix "arista-ale-counters-open-config-qos-interface-queue-common-types"; }
  import openconfig-qos { prefix "openconfig-qos"; }
  import openconfig-types { prefix "openconfig-types"; }
  
  organization
    "Arista Networks <http://arista.com/>";
  contact
    "Arista Networks <http://arista.com/>";
  
  description
    "This module contains VOQ queue interface state augments.
    THIS YANG MODULE WAS GENERATED. DO NOT EDIT THIS FILE.";
  
  oc-ext:openconfig-version "1.0.0";
  
  revision "2026-04-15" {
    description
      "Version 1.0.0, generated on 2026-04-15";
    reference "1.0.0";
  }
  grouping ale-counters-open-config-voq-delete-state {
    uses arista-ale-counters-open-config-qos-interface-queue-common-types:ale-counters-open-config-interface-queue-key;
    leaf last-voq-delete-source {
      type string;
      description
        "Ingress switch chip and core where VOQ deletes occurred.";
    }
    leaf last-voq-delete-timestamp {
      type openconfig-types:timeticks64;
      description
        "Timestamp of the last VOQ delete occurrence.";
    }
    description
      "ale-counters-open-config-voq-delete-state";
  }
  augment "/openconfig-qos:qos/openconfig-qos:interfaces/openconfig-qos:interface/openconfig-qos:output/openconfig-qos:queues/openconfig-qos:queue/openconfig-qos:state" {
    leaf last-voq-delete-source {
      type string;
      description
        "Ingress switch chip and core where VOQ deletes occurred.";
    }
    leaf last-voq-delete-timestamp {
      type openconfig-types:timeticks64;
      description
        "Timestamp of the last VOQ delete occurrence.";
    }
    description
      "Ingress switch chip and core where VOQ deletes occurred.
      Timestamp of the last VOQ delete occurrence.";
  }
} // augment-yang
