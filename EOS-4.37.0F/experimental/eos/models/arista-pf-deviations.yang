module arista-pf-deviations {
  namespace "http://arista.com/yang/openconfig/policy-forwarding/deviations";
  prefix arista-pf-deviations;

  import openconfig-network-instance {
    prefix oc-netinst;
  }
  import openconfig-extensions {
    prefix oc-ext;
  }
  organization
    "Arista Networks <http://arista.com/>";
  contact
    "Arista Networks, Inc.
     Product Support";
  description
    "This module contains OpenConfig policy forwarding deviations in Arista EOS.

     Copyright (c) 2026 Arista Networks, Inc. All rights reserved.";
  oc-ext:openconfig-version "1.0.0";

  revision 2026-06-08 {
    description
      "Initial deviation file.";
    reference
      "1.0.0";
  }

  deviation "/oc-netinst:network-instances/oc-netinst:network-instance/oc-netinst:policy-forwarding/oc-netinst:policies/oc-netinst:policy/oc-netinst:rules/oc-netinst:rule/oc-netinst:action/oc-netinst:config/oc-netinst:next-hop-group" {
    description
       "The leafref type is not supported. Workaround is to set to same type as leafref.";
    deviate replace  {
      type string;
    }
  }

  deviation "/oc-netinst:network-instances/oc-netinst:network-instance/oc-netinst:policy-forwarding/oc-netinst:policies/oc-netinst:policy/oc-netinst:rules/oc-netinst:rule/oc-netinst:action/oc-netinst:state/oc-netinst:next-hop-group" {
    description
       "The leafref type is not supported. Workaround is to set to same type as leafref.";
    deviate replace  {
      type string;
    }
  }
}
