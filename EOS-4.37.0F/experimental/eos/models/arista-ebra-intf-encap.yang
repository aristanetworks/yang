module arista-ebra-intf-encap {
  yang-version 1;
  namespace "http://arista.com/yang/experimental/eos/arista-ebra-intf-encap";
  prefix "arista-ebra-intf-encap";
  
  import openconfig-extensions { prefix "oc-ext"; }
  import arista-arnet-vlan-tag { prefix "arista-arnet-vlan-tag"; }
  import openconfig-interfaces { prefix "openconfig-interfaces"; }
  
  organization
    "Arista Networks <http://arista.com/>";
  contact
    "Arista Networks <http://arista.com/>";
  
  description
    "Defines encapsulations for interfaces
    THIS YANG MODULE WAS GENERATED. DO NOT EDIT THIS FILE.";
  
  oc-ext:openconfig-version "1.0.0";
  
  revision "2021-10-20" {
    description
      "Version 1.0.0, generated on 2021-10-20";
    reference "1.0.0";
  }
  typedef vlan-cos-source {
    type enumeration {
      enum EMPTY {
        value 0;
        description
          "Set CoS to zero";
      }
      enum TRAFFIC_CLASS {
        value 1;
        description
          "Derive CoS from traffic-class the packet traversed through";
      }
      enum OUTER {
        value 2;
        description
          "Derive CoS from from incoming outer tag";
      }
      enum INNER {
        value 3;
        description
          "Derive CoS from from incoming inner tag";
      }
    }
    description
      "Describes which incoming tag, if any, the CoS markings of the outgoing tags may be copied from.";
  }
  grouping intf-vlan-encap {
    leaf intf-id {
      type openconfig-interfaces:interface-id;
      description
        "The interface";
    }
    container encap {
      uses arista-arnet-vlan-tag:ebra-vlan-tag-encap;
      description
        "The tag values to match or manipulate";
    }
    description
      "A local interface, dynamic tunnel or a pseudowire remote connector along with tag values to match or manipulate with";
  }
  grouping vlan-cos-tuple {
    leaf src-outer-cos {
      type vlan-cos-source;
      description
        "CoS source of the outer source tag";
    }
    leaf src-inner-cos {
      type vlan-cos-source;
      description
        "CoS source of the inner source tag";
    }
    leaf dst-outer-cos {
      type vlan-cos-source;
      description
        "CoS source of the outer destination tag";
    }
    leaf dst-inner-cos {
      type vlan-cos-source;
      description
        "CoS source of the inner destination tag";
    }
    description
      "Fully specifies how CoS markings should be preserved for an encapsulation in either direction.";
  }
} // main-yang
