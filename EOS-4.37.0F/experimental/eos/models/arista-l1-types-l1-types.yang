module arista-l1-types-l1-types {
  yang-version 1;
  namespace "http://arista.com/yang/experimental/eos/arista-l1-types-l1-types";
  prefix "arista-l1-types-l1-types";
  
  import openconfig-extensions { prefix "oc-ext"; }
  
  organization
    "Arista Networks <http://arista.com/>";
  contact
    "Arista Networks <http://arista.com/>";
  
  description
    "L1 Types
    THIS YANG MODULE WAS GENERATED. DO NOT EDIT THIS FILE.";
  
  oc-ext:openconfig-version "1.0.0";
  
  revision "2025-07-29" {
    description
      "Version 1.0.0, generated on 2025-07-29";
    reference "1.0.0";
  }
  typedef hardware-phy-test-pattern {
    type enumeration {
      enum PATTERN_NONE {
        value 0;
        description
          "PATTERN_NONE";
      }
      enum PRBS_7 {
        value 1;
        description
          "PRBS_7";
      }
      enum PRBS_9 {
        value 2;
        description
          "PRBS_9";
      }
      enum PRBS_11 {
        value 3;
        description
          "PRBS_11";
      }
      enum PRBS_13 {
        value 4;
        description
          "PRBS_13";
      }
      enum PRBS_15 {
        value 5;
        description
          "PRBS_15";
      }
      enum PRBS_23 {
        value 6;
        description
          "PRBS_23";
      }
      enum PRBS_31 {
        value 7;
        description
          "PRBS_31";
      }
      enum PRBS_49 {
        value 8;
        description
          "PRBS_49";
      }
      enum PRBS_58 {
        value 9;
        description
          "PRBS_58";
      }
      enum PRBS_63 {
        value 10;
        description
          "PRBS_63";
      }
    }
    description
      "Test pattern enum";
  }
  typedef hardware-phy-test-pattern-lock {
    type enumeration {
      enum LOCK_NOT_APPLICABLE {
        value 0;
        description
          "NOT_APPLICABLE";
      }
      enum NOT_LOCKED {
        value 1;
        description
          "NOT_LOCKED";
      }
      enum LOCKED {
        value 2;
        description
          "LOCKED";
      }
    }
    description
      "Test pattern link lock enum";
  }
  typedef hardware-phy-test-pattern-lock-latch {
    type enumeration {
      enum LOCK_UNKNOWN {
        value 0;
        description
          "UNKNOWN";
      }
      enum WAITING_FOR_LOCK {
        value 1;
        description
          "WAITING_FOR_LOCK";
      }
      enum LOCK_LOST {
        value 2;
        description
          "LOST";
      }
      enum LOCK_NOT_LOST {
        value 3;
        description
          "NOT_LOST";
      }
    }
    description
      "Test pattern lock latch enum";
  }
  typedef hardware-phy-test-pattern-operational {
    type enumeration {
      enum SUCCESS {
        value 0;
        description
          "SUCCESS";
      }
      enum AUTONEG_ERROR {
        value 1;
        description
          "AUTONEG_ERROR";
      }
    }
    description
      "Status of PRBS configuration";
  }
} // main-yang
