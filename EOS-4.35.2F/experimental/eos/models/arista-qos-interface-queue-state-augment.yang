module arista-qos-interface-queue-state-augment {
  yang-version 1;
  namespace "http://arista.com/yang/experimental/eos/arista-qos-interface-queue-state-augment";
  prefix "arista-qos-interface-queue-state-augment";
  
  import openconfig-extensions { prefix "oc-ext"; }
  import openconfig-interfaces { prefix "openconfig-interfaces"; }
  import openconfig-types { prefix "openconfig-types"; }
  import openconfig-qos { prefix "openconfig-qos"; }
  organization
    "Arista Networks <http://arista.com/>";
  contact
    "Arista Networks <http://arista.com/>";
  description
    "This module contains VOQ queue interface state augments.
    
    THIS YANG MODULE WAS GENERATED. DO NOT EDIT THIS FILE.";
  
  oc-ext:openconfig-version "1.0.0";
  
  revision "2024-08-22" {
    description
      "Version 1.0.0, generated on 2024-08-22";
    reference "1.0.0";
  }
  
  grouping ale-counters-open-config-interface-queue-key {
    description
      "ale-counters-open-config-interface-queue-key";
  }
  
  grouping ale-counters-open-config-qos-interface-queue-state {
    leaf last-voq-delete-source {
      type string;
      description
        "Ingress switch chip and core where VOQ deletes occurred.";
    }
    leaf last-voq-delete-timestamp {
      type openconfig-types:timeticks64;
      description
        "Timestamp of the last VOQ delete occurrence.";
    }
    description
      "ale-counters-open-config-qos-interface-queue-state";
  }
  
  grouping ale-counters-open-config-open-config-qos-interface-queue-state {
    description
      "ale-counters-open-config-open-config-qos-interface-queue-state";
  }
  
  augment "/openconfig-qos:qos/openconfig-qos:interfaces/openconfig-qos:interface/openconfig-qos:output/openconfig-qos:queues/openconfig-qos:queue/openconfig-qos:state" {
    leaf last-voq-delete-source {
      type string;
      description
        "Ingress switch chip and core where VOQ deletes occurred.";
    }
    leaf last-voq-delete-timestamp {
      type openconfig-types:timeticks64;
      description
        "Timestamp of the last VOQ delete occurrence.";
    }
    description
      "Ingress switch chip and core where VOQ deletes occurred.
      Timestamp of the last VOQ delete occurrence.";
  }
} // augmented-yang
