module arista-xcvr-xcvr-test-pattern {
  yang-version 1;
  namespace "http://arista.com/yang/experimental/eos/arista-xcvr-xcvr-test-pattern";
  prefix "arista-xcvr-xcvr-test-pattern";
  
  import openconfig-extensions { prefix "oc-ext"; }
  organization
    "Arista Networks <http://arista.com/>";
  contact
    "Arista Networks <http://arista.com/>";
  description
    "Xcvr types
    
    THIS YANG MODULE WAS GENERATED. DO NOT EDIT THIS FILE.";
  
  oc-ext:openconfig-version "1.0.0";
  
  revision "2025-08-22" {
    description
      "Version 1.0.0, generated on 2025-08-22";
    reference "1.0.0";
  }
  
  typedef xcvr-test-pattern-type {
    type enumeration {
      enum PRBS_31_Q {
        value 0;
        description
          "PRBS_31_Q";
      }
      enum PRBS_31 {
        value 1;
        description
          "PRBS_31";
      }
      enum PRBS_23_Q {
        value 2;
        description
          "PRBS_23_Q";
      }
      enum PRBS_23 {
        value 3;
        description
          "PRBS_23";
      }
      enum PRBS_15_Q {
        value 4;
        description
          "PRBS_15_Q";
      }
      enum PRBS_15 {
        value 5;
        description
          "PRBS_15";
      }
      enum PRBS_13_Q {
        value 6;
        description
          "PRBS_13_Q";
      }
      enum PRBS_13 {
        value 7;
        description
          "PRBS_13";
      }
      enum PRBS_9_Q {
        value 8;
        description
          "PRBS_9_Q";
      }
      enum PRBS_9 {
        value 9;
        description
          "PRBS_9";
      }
      enum PRBS_7_Q {
        value 10;
        description
          "PRBS_7_Q";
      }
      enum PRBS_7 {
        value 11;
        description
          "PRBS_7";
      }
      enum SSPRQ {
        value 12;
        description
          "SSPRQ";
      }
      enum PATTERN_CUSTOM {
        value 14;
        description
          "PATTERN_CUSTOM";
      }
      enum PATTERN_USER {
        value 15;
        description
          "PATTERN_USER";
      }
    }
    description
      "Test pattern enum";
  }
  
} // main-yang
