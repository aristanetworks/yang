module arista-host-inject-ochost-inject-config {
  yang-version 1;
  namespace "http://arista.com/yang/experimental/eos/arista-host-inject-ochost-inject-config";
  prefix "arista-host-inject-ochost-inject-config";
  
  import openconfig-extensions { prefix "oc-ext"; }
  import arista-exp-eos { prefix "arista-exp-eos"; }
  import openconfig-inet-types { prefix "openconfig-inet-types"; }
  import openconfig-interfaces { prefix "openconfig-interfaces"; }
  organization
    "Arista Networks <http://arista.com/>";
  contact
    "Arista Networks <http://arista.com/>";
  description
    "Host injection config
    
    THIS YANG MODULE WAS GENERATED. DO NOT EDIT THIS FILE.";
  
  oc-ext:openconfig-version "1.0.0";
  
  revision "2025-01-30" {
    description
      "Version 1.0.0, generated on 2025-01-30";
    reference "1.0.0";
  }
  
  grouping host-inject-ochost-inject-key {
    leaf id {
      type openconfig-interfaces:interface-id;
      description
        "Name of the interface where the host route injections are applied.";
    }
    leaf name {
      type openconfig-inet-types:ip-prefix;
      description
        "The IP prefix used for host route injection.";
    }
    description
      "";
  }
  
  grouping host-inject-ochost-inject-v4 {
    leaf name {
      type openconfig-inet-types:ip-prefix;
      description
        "IPv4 prefix used for matching learned host routes.";
    }
    leaf host-route-prefix-length {
      type uint8;
      default 32;
      description
        "IPv4 prefix length used for exporting host routes as prefixes. Prefix length of 32 is the only supported value for the IPv4 case which indicates that host routes themselves are targeted for export.";
    }
    leaf preference {
      type uint8;
      default 250;
      description
        "Preference value associated to the given IP prefix.";
    }
    description
      "";
  }
  
  grouping host-inject-ochost-inject-v6 {
    leaf name {
      type openconfig-inet-types:ip-prefix;
      description
        "IPv6 prefix used for matching learned host routes.";
    }
    leaf host-route-prefix-length {
      type uint8;
      default 128;
      description
        "IPv6 prefix length used for exporting host routes as prefixes. For example, when 2001:4860:4860::8888::/128 is the host route targeted for export, having host-route-prefix-length of 48 will export 2001:4860:4860::/48.";
    }
    leaf preference {
      type uint8;
      default 250;
      description
        "Preference value associated to the given IP prefix.";
    }
    description
      "";
  }
  
  grouping host-inject-ochost-inject-v4-config-elem {
    uses host-inject-ochost-inject-key;
    container config {
      uses host-inject-ochost-inject-v4;
      description
        "Container representing configuration attributes for a given IPv4 prefix.";
    }
    description
      "";
  }
  
  grouping host-inject-ochost-inject-v6-config-elem {
    uses host-inject-ochost-inject-key;
    container config {
      uses host-inject-ochost-inject-v6;
      description
        "Container representing configuration attributes for a given IPv4 prefix.";
    }
    description
      "";
  }
  
  grouping host-inject-ochost-inject-v4-config-cmv {
    description
      "Container for IPv4 prefixes.";
  }
  
  grouping host-inject-ochost-inject-v6-config-cmv {
    description
      "Container for IPv6 prefixes.";
  }
  
  augment "/arista-exp-eos:arista" {
    container host-route-injections {
      list host-route-injection {
        key "id";
        leaf id {
          type string;
          description
            "id leaf used as key for host-route-injection list";
        }
        container ipv4 {
          container prefixes {
            list prefix {
              key "name";
              uses host-inject-ochost-inject-v4-config-elem;
              description
                "prefix list";
            }
            description
              "prefixes container";
          }
          description
            "ipv4 container";
        }
        container ipv6 {
          container prefixes {
            list prefix {
              key "name";
              uses host-inject-ochost-inject-v6-config-elem;
              description
                "prefix list";
            }
            description
              "prefixes container";
          }
          description
            "ipv6 container";
        }
        description
          "host-route-injection list";
      }
      description
        "host-route-injections container";
    }
  }
} // main-yang
