module arista-l1-open-config-phy-model {
  yang-version 1;
  namespace "http://arista.com/yang/experimental/eos/arista-l1-open-config-phy-model";
  prefix "arista-l1-open-config-phy-model";
  
  import openconfig-extensions { prefix "oc-ext"; }
  import arista-eos-types { prefix "arista-eos-types"; }
  import openconfig-if-ethernet { prefix "openconfig-if-ethernet"; }
  import openconfig-interfaces { prefix "openconfig-interfaces"; }
  organization
    "Arista Networks <http://arista.com/>";
  contact
    "Arista Networks <http://arista.com/>";
  description
    "Attributes related to interface phy components
    
    THIS YANG MODULE WAS GENERATED. DO NOT EDIT THIS FILE.";
  
  oc-ext:openconfig-version "1.0.0";
  
  revision "2023-12-05" {
    description
      "Version 1.0.0, generated on 2023-12-05";
    reference "1.0.0";
  }
  
  typedef l1-open-config-phy-phy-link-state {
    type enumeration {
      enum UNKNOWN {
        value 0;
        description
          "unknown";
      }
      enum INIT {
        value 1;
        description
          "init";
      }
      enum DETECTING_XCVR {
        value 2;
        description
          "detectingXcvr";
      }
      enum AUTONEGOTIATING {
        value 3;
        description
          "autonegotiating";
      }
      enum LINK_DOWN {
        value 4;
        description
          "linkDown";
      }
      enum LINK_UP {
        value 5;
        description
          "linkUp";
      }
      enum ERR_DISABLED {
        value 6;
        description
          "errDisabled";
      }
    }
    description
      "PhyLinkState";
  }
  
  grouping l1-open-config-phy-intf-phy-lane-index {
    leaf intf-name {
      type string;
      description
        "The interface name (eg, EthernetX/Y)";
    }
    leaf phy-index {
      type uint16;
      description
        "The index of the phy (0 is the phy in the ASIC)";
    }
    leaf lane {
      type uint16;
      description
        "The lane number (0 based)";
    }
    description
      "Index for a lane based phy attribute";
  }
  
  grouping l1-open-config-phy-intf-phy-index {
    leaf intf-name {
      type string;
      description
        "The interface name (eg, EthernetX/Y)";
    }
    leaf phy-index {
      type uint16;
      description
        "The index of the phy (0 is the phy in the ASIC)";
    }
    description
      "Index for a phy attribute";
  }
  
  grouping l1-open-config-phy-pcs-lane-state {
    uses l1-open-config-phy-intf-phy-lane-index;
    description
      "Lane based attributes for the physical coding sublayer";
  }
  
  grouping l1-open-config-phy-pcs-lane-ingress-container {
    leaf name {
      type string;
      description
        "name of the grouping";
    }
    description
      "Container for the ingress pcs lane component";
  }
  
  grouping l1-open-config-phy-pcs-lane-egress-container {
    leaf name {
      type string;
      description
        "name of the grouping";
    }
    description
      "Container for the egress pcs lane component";
  }
  
  grouping l1-open-config-phy-pcs-state {
    uses l1-open-config-phy-intf-phy-index;
    leaf error-blocks {
      type uint32;
      description
        "errorBlocks";
    }
    description
      "Attributes for the physical coding sublayer";
  }
  
  grouping l1-open-config-phy-pcs-ingress-container {
    leaf name {
      type string;
      description
        "name of the grouping";
    }
    description
      "Container for the ingress pcs component";
  }
  
  grouping l1-open-config-phy-pcs-egress-container {
    leaf name {
      type string;
      description
        "name of the grouping";
    }
    description
      "Container for the egress pcs component";
  }
  
  grouping l1-open-config-phy-fec-state {
    uses l1-open-config-phy-intf-phy-index;
    leaf pre-fec-ber {
      type binary {
        length 8;
      }
      description
        "preFecBer";
    }
    leaf uncorrected-codewords {
      type uint64;
      description
        "uncorrectedCodewords";
    }
    leaf corrected-symbol-rate {
      type binary {
        length 8;
      }
      description
        "correctedSymbolRate";
    }
    leaf corrected-codewords {
      type uint64;
      description
        "correctedCodewords";
    }
    description
      "Attributes for the forward error correction layer";
  }
  
  grouping l1-open-config-phy-fec-ingress-container {
    leaf name {
      type string;
      description
        "name of the grouping";
    }
    description
      "Container for the ingress fec component";
  }
  
  grouping l1-open-config-phy-fec-egress-container {
    leaf name {
      type string;
      description
        "name of the grouping";
    }
    description
      "Container for the egress fec component";
  }
  
  grouping l1-open-config-phy-rs-state {
    uses l1-open-config-phy-intf-phy-index;
    leaf link-state {
      type l1-open-config-phy-phy-link-state;
      description
        "linkState";
    }
    leaf last-link-state-change {
      type arista-eos-types:seconds;
      description
        "lastLinkStateChange";
    }
    leaf remote-fault {
      type boolean;
      description
        "remoteFault";
    }
    leaf last-remote-fault-change {
      type arista-eos-types:seconds;
      description
        "lastRemoteFaultChange";
    }
    leaf local-fault {
      type boolean;
      description
        "localFault";
    }
    leaf last-local-fault-change {
      type arista-eos-types:seconds;
      description
        "lastLocalFaultChange";
    }
    description
      "Attributes for the Rs coding sublayer";
  }
  
  grouping l1-open-config-phy-rs-ingress-container {
    description
      "Container for the ingress rs component";
  }
  
  augment "/openconfig-interfaces:interfaces/openconfig-interfaces:interface/openconfig-if-ethernet:ethernet" {
    container phys {
      list phy {
        key "index";
        leaf index {
          type string;
          description
            "index leaf used as key for phy list";
        }
        container ingress {
          container pcs {
            container lanes {
              list lane {
                key "lane";
                leaf lane {
                  type string;
                  description
                    "lane leaf used as key for lane list";
                }
                container state {
                  config false;
                  uses l1-open-config-phy-pcs-lane-state;
                  description
                    "state container";
                }
                description
                  "lane list";
              }
              description
                "lanes container";
            }
            container state {
              config false;
              uses l1-open-config-phy-pcs-state;
              description
                "state container";
            }
            description
              "pcs container";
          }
          container fec {
            container state {
              config false;
              uses l1-open-config-phy-fec-state;
              description
                "state container";
            }
            description
              "fec container";
          }
          container rs {
            container state {
              config false;
              uses l1-open-config-phy-rs-state;
              description
                "state container";
            }
            description
              "rs container";
          }
          description
            "ingress container";
        }
        container egress {
          container pcs {
            container lanes {
              list lane {
                key "lane";
                leaf lane {
                  type string;
                  description
                    "lane leaf used as key for lane list";
                }
                container state {
                  config false;
                  uses l1-open-config-phy-pcs-lane-state;
                  description
                    "state container";
                }
                description
                  "lane list";
              }
              description
                "lanes container";
            }
            container state {
              config false;
              uses l1-open-config-phy-pcs-state;
              description
                "state container";
            }
            description
              "pcs container";
          }
          container fec {
            container state {
              config false;
              uses l1-open-config-phy-fec-state;
              description
                "state container";
            }
            description
              "fec container";
          }
          description
            "egress container";
        }
        description
          "phy list";
      }
      description
        "phys container";
    }
  }
} // main-yang
