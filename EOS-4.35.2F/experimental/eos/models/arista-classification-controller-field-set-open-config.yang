module arista-classification-controller-field-set-open-config {
  yang-version 1;
  namespace "http://arista.com/yang/experimental/eos/arista-classification-controller-field-set-open-config";
  prefix "arista-classification-controller-field-set-open-config";
  
  import openconfig-extensions { prefix "oc-ext"; }
  import arista-exp-eos { prefix "arista-exp-eos"; }
  import arista-traffic-policy { prefix "arista-traffic-policy"; }
  import openconfig-inet-types { prefix "openconfig-inet-types"; }
  organization
    "Arista Networks <http://arista.com/>";
  contact
    "Arista Networks <http://arista.com/>";
  description
    "Traffic Policy Field Sets
    
    THIS YANG MODULE WAS GENERATED. DO NOT EDIT THIS FILE.";
  
  oc-ext:openconfig-version "1.0.0";
  
  revision "2024-02-06" {
    description
      "Version 1.0.0, generated on 2024-02-06";
    reference "1.0.0";
  }
  
  typedef classification-oc-controller-oc-field-set-config-type {
    type enumeration {
      enum STATIC {
        value 0;
        description
          "Config is added to the running-config";
      }
      enum CONTROLLER {
        value 1;
        description
          "Dynamic config populated by controller that is non-persistent across reloads";
      }
    }
    description
      "Field Set configuration source type";
  }
  
  grouping classification-oc-controller-oc-prefix {
    leaf prefix {
      type openconfig-inet-types:ip-prefix;
      description
        "Prefix";
    }
    description
      "Prefix";
  }
  
  grouping classification-oc-controller-oc-field-set-prefix-config {
    leaf name {
      type string;
      description
        "Field set name";
    }
    leaf config-type {
      type classification-oc-controller-oc-field-set-config-type;
      default STATIC;
      description
        "Field set config type ";
    }
    list prefixes {
      key "prefix";
      uses classification-oc-controller-oc-prefix;
      description
        "List of prefixes";
    }
    list exclude-prefixes {
      key "prefix";
      uses classification-oc-controller-oc-prefix;
      description
        "List of prefixes to exclude";
    }
    description
      "Prefix set config";
  }
  
  grouping classification-oc-controller-oc-ipv4-field-set-config-dir {
    leaf name {
      type string;
      description
        "name of the grouping";
    }
    description
      "IPv4 field set config directory";
  }
  
  grouping classification-oc-controller-oc-ipv6-field-set-config-dir {
    leaf name {
      type string;
      description
        "name of the grouping";
    }
    description
      "IPv6 field set config directory";
  }
  
  grouping classification-oc-controller-oc-ipv4-field-set-state-dir {
    leaf name {
      type string;
      description
        "name of the grouping";
    }
    description
      "IPv4 field set state directory";
  }
  
  grouping classification-oc-controller-oc-ipv6-field-set-state-dir {
    leaf name {
      type string;
      description
        "name of the grouping";
    }
    description
      "IPv6 field set state directory";
  }
  
  augment "/arista-exp-eos:arista/arista-traffic-policy:traffic-policy" {
    container field-sets {
      container ipv4-prefix-sets {
        list ipv4-prefix-set {
          key "name";
          leaf name {
            type string;
            description
              "name leaf used as key for ipv4-prefix-set list";
          }
          container config {
            uses classification-oc-controller-oc-field-set-prefix-config;
            description
              "config container";
          }
          container state {
            config false;
            uses classification-oc-controller-oc-field-set-prefix-config;
            description
              "state container";
          }
          description
            "ipv4-prefix-set list";
        }
        description
          "ipv4-prefix-sets container";
      }
      container ipv6-prefix-sets {
        list ipv6-prefix-set {
          key "name";
          leaf name {
            type string;
            description
              "name leaf used as key for ipv6-prefix-set list";
          }
          container config {
            uses classification-oc-controller-oc-field-set-prefix-config;
            description
              "config container";
          }
          container state {
            config false;
            uses classification-oc-controller-oc-field-set-prefix-config;
            description
              "state container";
          }
          description
            "ipv6-prefix-set list";
        }
        description
          "ipv6-prefix-sets container";
      }
      description
        "field-sets container";
    }
  }
} // main-yang
