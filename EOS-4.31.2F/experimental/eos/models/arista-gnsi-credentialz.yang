module arista-gnsi-credentialz {
  yang-version 1;
  namespace "http://arista.com/yang/experimental/eos/arista-gnsi-credentialz";
  prefix "arista-gnsi-credentialz";

  import openconfig-extensions { prefix "oc-ext"; }
  import openconfig-types { prefix "openconfig-types"; }
  organization
    "Arista Networks <http://arista.com/>";
  contact
    "Arista Networks <http://arista.com/>";
  description
    "This module provides a data model for the metadata
         of credentials installed on a networking device.

    THIS YANG MODULE WAS GENERATED. DO NOT EDIT THIS FILE.";

  oc-ext:openconfig-version "1.1.0";

  revision "2023-10-03" {
    description
      "Version 1.1.0, generated on 2023-10-03";
    reference "1.1.0";
  }

  // covered-by: openconfig-system.yang,gnsi-credentialz.yang
  grouping ssh-server-state {
    leaf active-trusted-user-ca-keys-version {
      type string;
      description
        "The version of the trusted SSH CA public key.";
    }
    leaf active-trusted-user-ca-keys-created-on {
      type openconfig-types:timeticks64;
      description
        "The timestamp of the moment when the trusted
               SSH CA public key was rotated.";
    }
    leaf active-host-certificate-version {
      type string;
      description
        "The version of the SSH host certificates.";
    }
    leaf active-host-certificate-created-on {
      type openconfig-types:timeticks64;
      description
        "The timestamp of the moment when the SSH host
                certificates were rotated.";
    }
    leaf active-host-key-version {
      type string;
      description
        "The version of the SSH host keys.";
    }
    leaf active-host-key-version-created-on {
      type openconfig-types:timeticks64;
      description
        "The timestamp of the moment when the
               SSH host keys were rotated";
    }
    description
      "";
  }
  grouping user-state {
    leaf password-version {
      type string;
      description
        "The version of the password that is currently used to
                    authenticate this user account.";
    }
    leaf password-created-on {
      type openconfig-types:timeticks64;
      description
        "The timestamp of the moment the currently used password has
                    been created.";
    }
    leaf authorized-users-list-version {
      type string;
      description
        "The version of the list of authorized users that is
                   currently associated with this system role.";
    }
    leaf authorized-users-list-created-on {
      type openconfig-types:timeticks64;
      description
        "The timestamp of the moment the currently used list of
                    authorized users has been created.";
    }
    leaf authorized-keys-list-version {
      type string;
      description
        "The version of the list of authorized keys that is currently
                    associated with this system role.";
    }
    leaf authorized-keys-list-created-on {
      type openconfig-types:timeticks64;
      description
        "The timestamp of the moment the currently used list of
                    authorized keys has been created.";
    }
    description
      "";
  }
  grouping user {
    leaf username {
      type string;
      description
        "";
    }
    container state {
      uses user-state;
      description
        "";
    }
    description
      "";
  }
  grouping users-dir {
    list user {
      key "username";
      uses user;
      description
        "";
    }
    description
      "";
  }
  grouping admin-user {
    container state {
      uses user-state;
      description
        "";
    }
    description
      "";
  }
  container system {
    container ssh-server {
      container state {
        config false;
        uses ssh-server-state;
        description
          "state container";
      }
      description
        "ssh-server container";
    }
    container aaa {
      container authentication {
        container users {
          config false;
          uses users-dir;
          description
            "users container";
        }
        container admin-user {
          config false;
          uses admin-user;
          description
            "admin-user container";
        }
        description
          "authentication container";
      }
      description
        "aaa container";
    }
    description
      "system container";
  }
}
