module arista-gnsi-certz {
  yang-version 1;
  namespace "http://arista.com/yang/experimental/eos/arista-gnsi-certz";
  prefix "arista-gnsi-certz";

  import openconfig-extensions { prefix "oc-ext"; }
  import openconfig-types { prefix "openconfig-types"; }
  organization
    "Arista Networks <http://arista.com/>";
  contact
    "Arista Networks <http://arista.com/>";
  description
    "This module provides a data model for the metadata
         of gRPC credentials installed on a networking device.

    THIS YANG MODULE WAS GENERATED. DO NOT EDIT THIS FILE.";

  oc-ext:openconfig-version "1.1.0";

  revision "2023-08-24" {
    description
      "Version 1.1.0, generated on 2023-08-24";
    reference "1.1.0";
  }

  // covered-by: openconfig-system.yang,gnsi-certz.yang
  grouping counters {
    leaf access-rejects {
      type uint64;
      description
        "The total number of times the gRPC
               denied access to the server.";
    }
    leaf last-access-reject {
      type openconfig-types:timeticks64;
      description
        "A timestamp of the last time the gRPC
               denied access to the server.";
    }
    leaf access-accepts {
      type uint64;
      description
        "The total number of times the gPRC
               allowed access to the server.";
    }
    leaf last-access-accept {
      type openconfig-types:timeticks64;
      description
        "A timestamp of the last time the gRPC
               allowed access to the server.";
    }
    description
      "A collection of counters that were collected while evaluating
              access to the gRPC server.";
  }
  grouping server-state {
    leaf certificate-version {
      type string;
      description
        "The version of the certificate (and associated
               private key) that is used by this gRPC server.";
    }
    leaf certificate-created-on {
      type openconfig-types:timeticks64;
      description
        "The timestamp of the moment when the certificate
               (and associated private key) that is currently used
               by this gRPC server was created.";
    }
    leaf ca-trust-bundle-version {
      type string;
      description
        "The version of the bundle of the Certificate
               Authority certificates a.k.a. trust bundle used by
               this gRPC server.";
    }
    leaf ca-trust-bundle-created-on {
      type openconfig-types:timeticks64;
      description
        "The timestamp of the moment when the bundle of
               the Certificate Authority certificates (a.k.a.
               trust bundle) was created.";
    }
    leaf certificate-revocation-list-bundle-version {
      type string;
      description
        "The version of the Certificate Revocation List
               bundle used by this gRPC server.";
    }
    leaf certificate-revocation-list-bundle-created-on {
      type openconfig-types:timeticks64;
      description
        "The timestamp of the moment when the
               Certificate Revocation List bundle was created.";
    }
    leaf authentication-policy-version {
      type string;
      description
        "The version of the authentication policy that
               is used by this gRPC server.";
    }
    leaf authentication-policy-created-on {
      type openconfig-types:timeticks64;
      description
        "The timestamp of the moment when the authentication
               policy that is currently used by this gRPC server was created.";
    }
    leaf ssl-profile-id {
      type string;
      description
        "The ID of this gRPC server's SSL profile
              as used by the gNSI Certz service";
    }
    container counters {
      uses counters;
      description
        "A collection of counters that were collected by
               the gRPC during the authentication process.";
    }
    description
      "";
  }
  grouping server {
    leaf name {
      type string;
      description
        "";
    }
    container state {
      uses server-state;
      description
        "A collection of counters that were collected by
               the gRPC during the authentication process.";
    }
    description
      "";
  }
  grouping grpc-server-dir {
    list grpc-server {
      key "name";
      uses server;
      description
        "";
    }
    description
      "";
  }
  container system {
    container grpc-servers {
      config false;
      uses grpc-server-dir;
      description
        "grpc-servers container";
    }
    description
      "system container";
  }
}
