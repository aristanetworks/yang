module arista-isis-augments {
  namespace "http://arista.com/yang/openconfig/isis/augments";
  prefix arista-isis-augments;

  import openconfig-network-instance {
    prefix oc-netinst;
  }
  import openconfig-isis {
    prefix oc-isis;
  }
  import openconfig-extensions {
    prefix oc-ext;
  }

  organization
    "Arista Networks, Inc.";
  contact
    "Arista Networks, Inc.
     Product Support";
  description
    "This module contains OpenConfig ISIS augments in Arista EOS.

     Copyright (c) 2018 Arista Networks, Inc. All rights reserved.";
  oc-ext:openconfig-version "1.10.0";

  revision 2022-04-07 {
    description
      "Added maximum-sid-depth base-mpls-imposition knob";
    reference
      "1.10.0";
  }

  revision 2022-03-17 {
    description
      "Remove authentication augments, as they are now available
      in the standard model";
    reference
      "1.9.0";
  }
  revision 2022-03-03 {
    description
      "Remove global hello-padding augmentations, as they are now
       available in the standard model";
    reference
      "1.8.0";
  }
  revision 2022-02-10 {
    description
      "Added csnp-enable-on-p2p-links knob";
    reference
      "1.7.0";
  }
  revision 2022-02-02 {
    description
      "Added hello-padding global type and config, state leaf";
    reference
      "1.6.0";
  }
  revision 2022-02-01 {
    description
      "Added auth-password leaf that was removed from official model";
    reference
      "1.5.1";
  }
  revision 2021-11-01 {
    description
      "Added LSDB size count to system-level-counters";
    reference
      "1.5.0";
  }
  revision 2021-09-27 {
    description
      "pyang auto format";
    reference
      "1.4.1";
  }
  revision 2021-07-14 {
    description
      "Added CSNP generation interval config to ISIS timers";
    reference
      "1.4.0";
  }
  revision 2021-04-13 {
    description
      "Added iid-tlv-check intf knob for ISIS multi instance";
    reference
      "1.3.0";
  }
  revision 2021-04-06 {
    description
      "Added lsp-rfc8202-rx-check knob for ISIS multi instance";
    reference
      "1.2.0";
  }
  revision 2021-03-25 {
    description
      "Added route limit information for routes redistributed to ISIS";
    reference
      "1.1.0";
  }
  revision 2021-02-03 {
    description
      "Added instance-id leaf under isis config";
    reference
      "1.0.4";
  }
  revision 2021-02-02 {
    description
      "Add augmentation for SR tunnel verification feature.";
    reference
      "1.0.3";
  }
  revision 2020-11-30 {
    description
      "Fix errors reported by pyang.";
    reference
      "1.0.2";
  }
  revision 2020-03-18 {
    description
      "Changed module prefix to arista-isis-augments.";
    reference
      "1.0.1";
  }
  revision 2018-01-12 {
    description
      "Initial augment file.";
    reference
      "1.0.0";
  }

  identity MAXIMUM_SID_DEPTH {
    description "Base indentity to define maximum SID depth type";
  }

  identity BASE_MPLS_IMPOSITION {
    base MAXIMUM_SID_DEPTH;
    description
      "Maximum SID depth type base MPLS imposition is set to
      advertise MPLS label stack size in MSD sub-TLV ";
  }

  augment "/oc-netinst:network-instances/oc-netinst:network-instance/oc-netinst:protocols/oc-netinst:protocol/oc-netinst:isis/oc-netinst:global/oc-netinst:afi-safi/oc-netinst:af/oc-netinst:multi-topology/oc-netinst:config" {
    uses oc-isis:rt-admin-config;
    description
      "Add admin-config to ISIS multi-topology address-family configuration.";
  }

  augment "/oc-netinst:network-instances/oc-netinst:network-instance/oc-netinst:protocols/oc-netinst:protocol/oc-netinst:isis/oc-netinst:global/oc-netinst:lsp-bit/oc-netinst:attached-bit/oc-netinst:config" {
    leaf ignore-bit {
      type boolean;
      description
        "EOS is capabale of suporting this configuration per Address Family.
         However, since the YANG model has no support per AF, this YANG leaf
         is set to true only when it is true for both AFs on EOS,
         else it remains false.";
    }
    description
      "Add ignore-bit to ISIS configuration.";
  }

  augment "/oc-netinst:network-instances/oc-netinst:network-instance/oc-netinst:protocols/oc-netinst:protocol/oc-netinst:isis/oc-netinst:global/oc-netinst:afi-safi/oc-netinst:af/oc-netinst:config" {
    leaf max-ecmp-paths {
      type uint32;
      description
        "ISIS max-paths count.";
    }
    description
      "Add max ECMP paths to ISIS configuration.";
  }

  augment "/oc-netinst:network-instances/oc-netinst:network-instance/oc-netinst:protocols/oc-netinst:protocol/oc-netinst:isis/oc-netinst:global/oc-netinst:afi-safi/oc-netinst:af/oc-netinst:state" {
    leaf max-ecmp-paths {
      type uint32;
      description
        "ISIS max-paths count.";
    }
    description
      "Add max ECMP paths to ISIS state.";
  }

  augment "/oc-netinst:network-instances/oc-netinst:network-instance/oc-netinst:protocols/oc-netinst:protocol/oc-netinst:isis/oc-netinst:global/oc-netinst:timers/oc-netinst:config" {
    description
      "Add CSNP generation interval to ISIS configuration.";
    leaf csnp-generation-interval {
      type uint32 {
        range "1..300";
      }
      units "seconds";
      default "10";
      description
        "The interval, specified in seconds, at which periodic CSNP packets should be transmitted by the local IS.";
    }
  }

  augment "/oc-netinst:network-instances/oc-netinst:network-instance/oc-netinst:protocols/oc-netinst:protocol/oc-netinst:isis/oc-netinst:global/oc-netinst:timers/oc-netinst:state" {
    description
      "Add CSNP generation interval to ISIS state.";
    leaf csnp-generation-interval {
      type uint32 {
        range "1..300";
      }
      units "seconds";
      default "10";
      description
        "The interval, specified in seconds, at which periodic CSNP packets should be transmitted by the local IS.";
    }
  }

  augment "/oc-netinst:network-instances/oc-netinst:network-instance/oc-netinst:protocols/oc-netinst:protocol/oc-netinst:isis/oc-netinst:interfaces/oc-netinst:interface/oc-netinst:levels/oc-netinst:level/oc-netinst:adjacencies/oc-netinst:adjacency/oc-netinst:state" {
    leaf advertised-hold-time {
      type uint16;
      description
        "Holding time in seconds as advertised by the neighbor for adjacency";
    }
    description
      "Add holding time to ISIS neighbor adjacency state.";
  }

  augment "/oc-netinst:network-instances/oc-netinst:network-instance/oc-netinst:protocols/oc-netinst:protocol/oc-netinst:isis/oc-netinst:global/oc-netinst:segment-routing/oc-netinst:config" {
    leaf segment-path-verification {
      type boolean;
      default "false";
      description
        "Enable path verification for prefix and adjacency segments";
    }
    description
      "Add segment-path-verification to ISIS configuration.";
  }

  augment "/oc-netinst:network-instances/oc-netinst:network-instance/oc-netinst:protocols/oc-netinst:protocol/oc-netinst:isis/oc-netinst:global/oc-netinst:segment-routing/oc-netinst:state" {
    leaf segment-path-verification {
      type boolean;
      default "false";
      description
        "Enable path verification for prefix and adjacency segments";
    }
    description
      "Add segment-path-verification to ISIS state.";
  }

  augment "/oc-netinst:network-instances/oc-netinst:network-instance/oc-netinst:protocols/oc-netinst:protocol/oc-netinst:isis/oc-netinst:global/oc-netinst:config" {
    leaf instance-id {
      type uint16;
      default "0";
      description
        "ISIS Instance ID";
    }
    description
      "Instance Identifier for ISIS instances.";
  }

  augment "/oc-netinst:network-instances/oc-netinst:network-instance/oc-netinst:protocols/oc-netinst:protocol/oc-netinst:isis/oc-netinst:global/oc-netinst:state" {
    leaf instance-id {
      type uint16;
      default "0";
      description
        "ISIS Instance ID";
    }
    description
      "Instance Identifier for ISIS instances.";
  }

  augment "/oc-netinst:network-instances/oc-netinst:network-instance/oc-netinst:protocols/oc-netinst:protocol/oc-netinst:isis/oc-netinst:global/oc-netinst:config" {
    leaf csnp-enable-on-p2p-links {
      type boolean;
      default "false";
      description
        "When this leaf is set to true, CSNP packets are transmitted periodically on P2P links.";
    }
    description
      "Add csnp-enable-on-p2p-links knob to ISIS configuration.";
  }

  augment "/oc-netinst:network-instances/oc-netinst:network-instance/oc-netinst:protocols/oc-netinst:protocol/oc-netinst:isis/oc-netinst:global/oc-netinst:state" {
    leaf csnp-enable-on-p2p-links {
      type boolean;
      default "false";
      description
        "When this leaf is set to true, CSNP packets are transmitted periodically on P2P links.";
    }
    description
      "Add csnp-enable-on-p2p-links knob to ISIS state.";
  }

  augment "/oc-netinst:network-instances/oc-netinst:network-instance/oc-netinst:protocols/oc-netinst:protocol/oc-netinst:isis/oc-netinst:global/oc-netinst:config" {
    leaf-list maximum-sid-depth {
      type identityref {
        base MAXIMUM_SID_DEPTH;
      }
      description
        "When the maximum-sid-depth type is added in list, Node MSD sub-TLV is advertised in router capability TLV.";
    }
    description
      "The list of enabled maximum SID depth type advertisement in IS-IS config.";
  }

  augment "/oc-netinst:network-instances/oc-netinst:network-instance/oc-netinst:protocols/oc-netinst:protocol/oc-netinst:isis/oc-netinst:global/oc-netinst:state" {
    leaf-list maximum-sid-depth {
      type identityref {
        base MAXIMUM_SID_DEPTH;
      }
      description
        "When the maximum-sid-depth type is added in list, Node MSD sub-TLV is advertised in router capability TLV.";
    }
    description
      "The list of enabled maximum SID depth type advertisement in IS-IS state.";
  }

  grouping isis-redistributed-route-limit-config {
    description
      "This grouping defines limit for routes redistributed into ISIS.";
    leaf route-limit {
      type uint32 {
        range "0..40000";
      }
      default "0";
      description
        "The maximum number of redistributed routes allowed per ISIS instance";
    }
  }

  augment "/oc-netinst:network-instances/oc-netinst:network-instance/oc-netinst:protocols/oc-netinst:protocol/oc-netinst:isis/oc-netinst:levels/oc-netinst:level" {
    description
      "Augment the ISIS level config to include route limit for redistributed routes
       into ISIS.";
    container redistributed-route-limit {
      description
        "Route limit configuration and operational state related to route
         redistribution into ISIS.";
      container config {
        description
          "Redistributed route limit configuration";
        uses isis-redistributed-route-limit-config;
      }
      container state {
        config false;
        description
          "Redistributed route limit state information";
        uses isis-redistributed-route-limit-config;
      }
    }
  }

  augment "/oc-netinst:network-instances/oc-netinst:network-instance/oc-netinst:protocols/oc-netinst:protocol/oc-netinst:isis/oc-netinst:global/oc-netinst:config" {
    leaf lsp-rfc8202-rx-check {
      type boolean;
      default "true";
      description
        "IID-TLV check knob for LSPs";
    }
    description
      "When set to true, accepts LSPs only with IID TLVs. When set to false, accepts LSPs without IID TLVs";
  }

  augment "/oc-netinst:network-instances/oc-netinst:network-instance/oc-netinst:protocols/oc-netinst:protocol/oc-netinst:isis/oc-netinst:global/oc-netinst:state" {
    leaf lsp-rfc8202-rx-check {
      type boolean;
      default "true";
      description
        "IID-TLV check knob for LSPs";
    }
    description
      "When set to true, accepts LSPs only with IID TLVs. When set to false, accepts LSPs without IID TLVs";
  }

  augment "/oc-netinst:network-instances/oc-netinst:network-instance/oc-netinst:protocols/oc-netinst:protocol/oc-netinst:isis/oc-netinst:levels/oc-netinst:level/oc-netinst:system-level-counters/oc-netinst:state" {
    leaf lsdb-size {
      type uint32;
      description
        "Number of LSPs in the link state database at this level";
    }
    description
      "Number of LSPs in the link state database at this level";
  }

  augment "/oc-netinst:network-instances/oc-netinst:network-instance/oc-netinst:protocols/oc-netinst:protocol/oc-netinst:isis/oc-netinst:interfaces/oc-netinst:interface/oc-netinst:config" {
    leaf iid-tlv-check {
      type boolean;
      default "true";
      description
        "IID-TLV check knob for hello packets";
    }
    description
      "Accepts hello PDUs without or mismatching IID TLVs when set to false";
  }

  augment "/oc-netinst:network-instances/oc-netinst:network-instance/oc-netinst:protocols/oc-netinst:protocol/oc-netinst:isis/oc-netinst:interfaces/oc-netinst:interface/oc-netinst:state" {
    leaf iid-tlv-check {
      type boolean;
      default "true";
      description
        "IID-TLV check knob for hello packets";
    }
    description
      "Accepts hello PDUs without or mismatching IID TLVs when set to false";
  }
}
