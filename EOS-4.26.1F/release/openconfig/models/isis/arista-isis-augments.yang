module arista-isis-augments {
  namespace "http://arista.com/yang/openconfig/isis/augments";
  prefix arista-isis-augments;

  import openconfig-network-instance {
    prefix oc-netinst;
  }
  import openconfig-isis {
    prefix oc-isis;
  }
  import openconfig-extensions {
    prefix oc-ext;
  }

  organization
    "Arista Networks, Inc.";
  contact
    "Arista Networks, Inc.
     Product Support";
  description
    "This module contains OpenConfig ISIS augments in Arista EOS.

     Copyright (c) 2018 Arista Networks, Inc. All rights reserved.";
  oc-ext:openconfig-version "1.0.2";

  revision 2021-02-03 {
    description
      "Added instance-id leaf under isis config";
    reference
      "1.0.4";
  }
  revision 2021-02-02 {
    description
      "Add augmentation for SR tunnel verification feature.";
    reference
      "1.0.3";
  }
  revision 2020-11-30 {
    description
      "Fix errors reported by pyang.";
    reference
      "1.0.2";
  }
  revision 2020-03-18 {
    description
      "Changed module prefix to arista-isis-augments.";
    reference
      "1.0.1";
  }
  revision 2018-01-12 {
    description
      "Initial augment file.";
    reference
      "1.0.0";
  }

  augment "/oc-netinst:network-instances/oc-netinst:network-instance/oc-netinst:protocols/oc-netinst:protocol/oc-netinst:isis/oc-netinst:global/oc-netinst:afi-safi/oc-netinst:af/oc-netinst:multi-topology/oc-netinst:config" {
    uses oc-isis:rt-admin-config;
    description
      "Add admin-config to ISIS multi-topology address-family configuration.";
  }

  augment "/oc-netinst:network-instances/oc-netinst:network-instance/oc-netinst:protocols/oc-netinst:protocol/oc-netinst:isis/oc-netinst:global/oc-netinst:lsp-bit/oc-netinst:attached-bit/oc-netinst:config" {
    leaf ignore-bit {
      type boolean;
      description
        "EOS is capabale of suporting this configuration per Address Family.
         However, since the YANG model has no support per AF, this YANG leaf
         is set to true only when it is true for both AFs on EOS,
         else it remains false.";
    }
    description
      "Add ignore-bit to ISIS configuration.";
  }

  augment "/oc-netinst:network-instances/oc-netinst:network-instance/oc-netinst:protocols/oc-netinst:protocol/oc-netinst:isis/oc-netinst:global/oc-netinst:afi-safi/oc-netinst:af/oc-netinst:config" {
    leaf max-ecmp-paths {
      type uint32;
      description
        "ISIS max-paths count.";
    }
    description
      "Add max ECMP paths to ISIS configuration.";
  }

  augment "/oc-netinst:network-instances/oc-netinst:network-instance/oc-netinst:protocols/oc-netinst:protocol/oc-netinst:isis/oc-netinst:global/oc-netinst:afi-safi/oc-netinst:af/oc-netinst:state" {
    leaf max-ecmp-paths {
      type uint32;
      description
        "ISIS max-paths count.";
    }
    description
      "Add max ECMP paths to ISIS state.";
  }

  augment "/oc-netinst:network-instances/oc-netinst:network-instance/oc-netinst:protocols/oc-netinst:protocol/oc-netinst:isis/oc-netinst:interfaces/oc-netinst:interface/oc-netinst:levels/oc-netinst:level/oc-netinst:adjacencies/oc-netinst:adjacency/oc-netinst:state" {
    leaf advertised-hold-time {
      type uint16;
      description
        "Holding time in seconds as advertised by the neighbor for adjacency";
    }
    description
      "Add holding time to ISIS neighbor adjacency state.";
  }

  augment "/oc-netinst:network-instances/oc-netinst:network-instance/oc-netinst:protocols/oc-netinst:protocol/oc-netinst:isis/oc-netinst:global/oc-netinst:segment-routing/oc-netinst:config" {
    leaf segment-path-verification {
      type boolean;
      default "false";
      description
        "Enable path verification for prefix and adjacency segments";
    }
    description
      "Add segment-path-verification to ISIS configuration.";
  }

  augment "/oc-netinst:network-instances/oc-netinst:network-instance/oc-netinst:protocols/oc-netinst:protocol/oc-netinst:isis/oc-netinst:global/oc-netinst:segment-routing/oc-netinst:state" {
    leaf segment-path-verification {
      type boolean;
      default "false";
      description
        "Enable path verification for prefix and adjacency segments";
    }
    description
      "Add segment-path-verification to ISIS state.";
  }

  augment "/oc-netinst:network-instances/oc-netinst:network-instance/oc-netinst:protocols/oc-netinst:protocol/oc-netinst:isis/oc-netinst:global/oc-netinst:config" {
    leaf instance-id {
      type uint16;
      default "0";
      description
        "ISIS Instance ID";
    }
    description
      "Instance Identifier for ISIS instances.";
  }

  augment "/oc-netinst:network-instances/oc-netinst:network-instance/oc-netinst:protocols/oc-netinst:protocol/oc-netinst:isis/oc-netinst:global/oc-netinst:state" {
    leaf instance-id {
      type uint16;
      default "0";
      description
        "ISIS Instance ID";
    }
    description
      "Instance Identifier for ISIS instances.";
  }
}
