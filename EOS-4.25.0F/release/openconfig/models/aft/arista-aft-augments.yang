module arista-aft-augments {
  namespace "http://arista.com/yang/openconfig/aft/augments";
  prefix arista-aft-augments;

  import openconfig-network-instance {
    prefix oc-netinst;
  }

  organization
    "Arista Networks, Inc.";
  contact
    "Arista Networks, Inc.
     Product Support";
  description
    "This module contains OpenConfig AFT augments in Arista EOS.

     Copyright (c) 2019 Arista Networks, Inc. All rights reserved.";

  revision 2019-10-01 {
    description
      "Initial augment file.";
  }

  grouping nexthop-counter-summary {
    description
      "Statistics for ECMP nexthops";
    leaf nexthop-ecmp-max-entries {
      type uint32;
      description
        "The maximum supported number of ECMP nexthop entries.";
    }
    leaf nexthop-ecmp-max-sets {
      type uint32;
      description
        "The maximum supported number of ECMP nexthop sets.";
    }
    leaf nexthop-ecmp-entries {
      type uint32;
      description
        "The number of currently used ECMP nexthop entries.";
    }
    leaf nexthop-ecmp-sets {
      type uint32;
      description
        "The number of currently used ECMP nexthop sets.";
    }
    leaf nexthop-ecmp-overlay-max-entries {
      type uint32;
      description
        "The maximum supported number of ECMP (overlay) nexthop entries.";
    }
    leaf nexthop-ecmp-overlay-max-sets {
      type uint32;
      description
        "The maximum supported number of ECMP (overlay) nexthop sets.";
    }
    leaf nexthop-ecmp-overlay-entries {
      type uint32;
      description
        "The number of currently used ECMP (overlay) nexthop entries.";
    }
    leaf nexthop-ecmp-overlay-sets {
      type uint32;
      description
        "The number of currently used ECMP (overlay) nexthop sets.";
    }
    leaf nexthop-ecmp-underlay-max-entries {
      type uint32;
      description
        "The maximum supported number of ECMP (underlay) nexthop entries.";
    }
    leaf nexthop-ecmp-underlay-max-sets {
      type uint32;
      description
        "The maximum supported number of ECMP (underlay) nexthop sets.";
    }
    leaf nexthop-ecmp-underlay-entries {
      type uint32;
      description
        "The number of currently used ECMP (underlay) nexthop entries.";
    }
    leaf nexthop-ecmp-underlay-sets {
      type uint32;
      description
        "The number of currently used ECMP (underlay) nexthop sets.";
    }
  }

  augment "/oc-netinst:network-instances/oc-netinst:network-instance/oc-netinst:afts" {
    container nexthop-ecmp-counters {
      description
        "Statistics for ECMP nexthops";
      container state {
        config false;
        description
          "State parameters for ECMP nexthops";
        uses nexthop-counter-summary;
      }
    }
  }
}
